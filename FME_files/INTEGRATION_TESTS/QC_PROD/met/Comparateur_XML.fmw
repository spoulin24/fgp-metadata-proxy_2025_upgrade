FME workspace Comparateur_XML.fmw

Parameters:
- ETALON_XML = C:\Users\stpoulin\Documents\Repos\fgp-metadata-proxy-master_10-21-25\FME_files\INTEGRATION_TESTS\AB_PROD\met\TEMP_C2020_DATA_2025-10-22114537%h - Copy\PT_Harvester\AB\XML_LOCAL\AB_00cb1008-cb4f-4fe7-86ce-0c85cb7b0409.xml
- RESULTAT_XML = C:\Users\stpoulin\Documents\Repos\fgp-metadata-proxy-master_10-21-25\FME_files\INTEGRATION_TESTS\AB_PROD\met\TEMP_C2025_DATA_2025-10-21103244%h\PT_Harvester\AB\XML_LOCAL\AB_00cb1008-cb4f-4fe7-86ce-0c85cb7b0409.xml
- PATHS_TO_IGNORE = /MD_Metadata/dateStamp,/MD_Metadata/contact/CI_ResponsibleParty/organisationName

Bookmark: Comparateur_XML_2020
Creator
    GEOMTYPE = Geometry Object
    NUM = 1
    CREATED -> ETALON_XML [INITIATOR]
    CREATED -> RESULTAT_XML [INITIATOR]
ChangeDetector
    BLANK_AND_MISSING_DIFFER = No
    BLANK_AND_MISSING_NAMES_TRAITS_DIFFER = No
    CHECK_COORDINATE_SYSTEMS = No
    CHECK_TYPES_AND_ENCODINGS = No
    LENIENT_MATCH = No
    MATCH = FULL
    MATCH_STRATEGY = Match All Attributes
    UNCHANGED_OUTPUT = Output Original
    UPDATED_LIST_NAME = list
    UPDATED -> ChangeDetector_Inserted
    INSERTED -> ChangeDetector_Inserted
    DELETED -> ChangeDetector_Inserted
ChangeDetector_Inserted: Logger
    LOG_FEATURE = LOG_RECORD
    MAXCOORDS = 20
    MAXFEATS = 20
    MESSAGE:
      HHHHHHHHHHHHHHHHHHHHHHHHHHHHHHHHHHHHHHHHHHHHHHHHHHHHHHHHHHHHHHHHHHHHHHH
      H                                                                   BEGIN                                                                                    H
      HHHHHHHHHHHHHHHHHHHHHHHHHHHHHHHHHHHHHHHHHHHHHHHHHHHHHHHHHHHHHHHHHHHHHHH
      -----------------------
      @Value(fileIdentifier.CharacterString)
      -----------------------
      HHHHHHHHHHHHHHHHHHHHHHHHHHHHHHHHHHHHHHHHHHHHHHHHHHHHHHHHHHHHHHHHHHHHHHH
      H                                                                   END                                                                                       H
      HHHHHHHHHHHHHHHHHHHHHHHHHHHHHHHHHHHHHHHHHHHHHHHHHHHHHHHHHHHHHHHHHHHHHHH
    SEVERITY = ERROR
    LOGGED -> ChangeDetector_Deleted
ChangeDetector_Deleted: Logger
    LOG_FEATURE = LOG_RECORD
    MAXCOORDS = 20
    MAXFEATS = 20
    MESSAGE:
      HHHHHHHHHHHHHHHHHHHHHHHHHHHHHHHHHHHHHHHHHHHHHHHHHHHHHHHHHHHHHHHHHHHHHHH
      H                                                                   BEGIN                                                                                    H
      HHHHHHHHHHHHHHHHHHHHHHHHHHHHHHHHHHHHHHHHHHHHHHHHHHHHHHHHHHHHHHHHHHHHHHH
      -----------------------
      @Value(fileIdentifier.CharacterString)
      -----------------------
      HHHHHHHHHHHHHHHHHHHHHHHHHHHHHHHHHHHHHHHHHHHHHHHHHHHHHHHHHHHHHHHHHHHHHHH
      H                                                                   END                                                                                       H
      HHHHHHHHHHHHHHHHHHHHHHHHHHHHHHHHHHHHHHHHHHHHHHHHHHHHHHHHHHHHHHHHHHHHHHH
    SEVERITY = INFO
    LOGGED -> FeatureHolder
FeatureHolder
    -> Terminator
Terminator
    MESSAGE:
      Translation Terminated. See logger.
      @Value(fileIdentifier.CharacterString) has differences

Bookmark: ETALON_XML Processing
ETALON_XML: FeatureReader
    ATTRIBUTES =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
    ATTR_ACCUM_MODE = Only Use Result
    COMBINE_GEOM = Use Result
    DATASET = $(ETALON_XML)
    FORMAT = XML
    INTERACT = <No Spatial Filter>
    OUTPUT_FEATURES_DISPLAY = Schema and Data Features
    XML_CONTINUE_ON_GEOM_ERROR = no
    XML_FILE_TYPE = Feature Paths
    XML_USE_SEARCH_ENVELOPE = NO
    XML_VALIDATE_DATASET = no
    XML_VALIDATE_XFMAP = no
    XML_XFMAP_FEATURE_PATHS = MD_Metadata
    XML_XFMAP_FEATURE_PATHS_STRUCTURE:
      <structure
      separator="."
      map-empty-elements="yes"
      matched-prefix="attributes"
      matched-attributes="yes"
      cardinality="+{?}"
      except-expression=""
      structure-prefix=""
      child-position-attribute=""
      attribute-identifier=""
      ui-mode="basic"/>
    MD_Metadata -> XMLFlattener
XMLFlattener
    EMBEDDED_EXPRESSIONS = MD_Metadata
    FEATURE_TYPES_FORMAT_NAME = XML
    FILE_XML = $(ETALON_XML)
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = XML file
    -> AttributeManager
AttributeManager
    ATTR_TABLE:
      REMOVE dateStamp.Date
      REMOVE xml_fragment
    -> AttributeExploder
AttributeExploder
    ATTR_NAME_LABEL = _attr_name
    ATTR_VALUE_LABEL = _attr_value
    EXPLODING_TYPE = Features
    KEEP_ATTRIBUTES = Yes
    KEEP_GEOMETRY = Yes
    -> StringSearcher
StringSearcher
    CASE = no
    MATCHED_PARTS_ATTR = _matches
    MATCHED_RESULT_ATTR = _first_match
    REGEXP = ^(.*?)(\{\d+\})(.*)$
    STRING_TO_SEARCH = @Value(_attr_name)
    MATCHED -> StringConcatenator
    NOT_MATCHED -> AttributeRenamer_3
Aggregator
    ACCUM_ATTRS_NAME = Drop Incoming Attributes
    GROUP_BY = fileIdentifier.CharacterString
    LIST_ATTRS_TO_INCLUDE = final_name final_value
    LIST_NAME = _attrs
    MODE = Attributes Only
    SEP = ,
    AGGREGATE -> ListExploder
ListExploder
    ATTR_ACCUM_MODE = Merge List Attributes
    ATTR_CONFLICT_RES = Use List Attribute Values
    LIST_ATTR = _attrs{}
    ELEMENTS -> AttributeCreator
AttributeCreator
    ATTR_TABLE = SET_TO @Value(final_name) = @Value(final_value)
    -> TestFilter_2
TestFilter_2
    DEFAULT_VALUE = <UNFILTERED>
    TEST_LIST = "BOOL_OP,OR,COMPOSITE_TEST,""""""1"""""",TEST_CLAUSE,TEST @Value(final_name) != _xml_source_",@Value(final_name) != _xml_source_
    @Value(final_name) != _xml_source_ -> ChangeDetector [ORIGINAL]

Bookmark: Matched - Lists
StringConcatenator
    ACTION = Create New Attribute
    PARM_LINE = fme_basicstring:24%24:@Value(_matches{0}.part)@Value(_matches{2}.part)
    VAL_ATTR = _list_name
    -> AttributeRenamer
AttributeRenamer
    ATTR_TABLE = RENAME_SET_DEFAULT _attr_value > _list_value
    -> ListBuilder
ListBuilder
    GROUP_BY = _list_name fileIdentifier.CharacterString
    LIST_ATTRS_TO_INCLUDE = _list_value
    LIST_NAME = _values
    -> ListSorter
ListSorter
    ORDER = Ascending
    SRC_LIST = _values{}._list_value
    TYPE = Alphabetic
    -> ListConcatenator
ListConcatenator
    DROP_EMPTY_PARTS = No
    LIST_ATTR = _values{}._list_value
    SEP = |
    VAL_ATTR = final_value
    -> AttributeRenamer_2
AttributeRenamer_2
    ATTR_TABLE = RENAME_SET_DEFAULT _list_name > final_name
    -> Aggregator

Bookmark: Unmatch - Non-list Attributes
AttributeRenamer_3
    ATTR_TABLE:
      RENAME_SET_DEFAULT _attr_name > final_name
      RENAME_SET_DEFAULT _attr_value > final_value
    -> Aggregator

Bookmark: RESULTAT_XML Processing
RESULTAT_XML: FeatureReader
    ATTRIBUTES =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
    ATTR_ACCUM_MODE = Only Use Result
    COMBINE_GEOM = Use Result
    DATASET = $(RESULTAT_XML)
    FORMAT = XML
    INTERACT = <No Spatial Filter>
    OUTPUT_FEATURES_DISPLAY = Schema and Data Features
    XML_CONTINUE_ON_GEOM_ERROR = no
    XML_FILE_TYPE = Feature Paths
    XML_USE_SEARCH_ENVELOPE = NO
    XML_VALIDATE_DATASET = no
    XML_VALIDATE_XFMAP = no
    XML_XFMAP_FEATURE_PATHS = MD_Metadata
    XML_XFMAP_FEATURE_PATHS_STRUCTURE:
      <structure
      separator="."
      map-empty-elements="yes"
      matched-prefix="attributes"
      matched-attributes="yes"
      cardinality="+{?}"
      except-expression=""
      structure-prefix=""
      child-position-attribute=""
      attribute-identifier=""
      ui-mode="basic"/>
    MD_Metadata -> XMLFlattener_2
XMLFlattener_2
    EMBEDDED_EXPRESSIONS = MD_Metadata
    FEATURE_TYPES_FORMAT_NAME = XML
    FILE_XML = $(RESULTAT_XML)
    FLATTEN_OPTIONS:
      <structure
      separator="."
      map-empty-elements="yes"
      matched-prefix="attributes"
      matched-attributes="yes"
      cardinality="+{?}"
      except-expression=""
      structure-prefix=""
      child-position-attribute=""
      attribute-identifier=""
      ui-mode="basic"/>
    XML_SOURCE_TYPE = XML file
    -> AttributeManager_2
AttributeManager_2
    ATTR_TABLE:
      REMOVE dateStamp.Date
      REMOVE xml_fragment
    -> AttributeExploder_2
AttributeExploder_2
    ATTR_NAME_LABEL = _attr_name
    ATTR_VALUE_LABEL = _attr_value
    EXPLODING_TYPE = Features
    KEEP_ATTRIBUTES = Yes
    KEEP_GEOMETRY = Yes
    -> StringSearcher_2
StringSearcher_2
    CASE = no
    MATCHED_PARTS_ATTR = _matches
    MATCHED_RESULT_ATTR = _first_match
    REGEXP = ^(.*?)(\{\d+\})(.*)$
    STRING_TO_SEARCH = @Value(_attr_name)
    MATCHED -> StringConcatenator_2
    NOT_MATCHED -> AttributeRenamer_6
Aggregator_3
    ACCUM_ATTRS_NAME = Drop Incoming Attributes
    GROUP_BY = fileIdentifier.CharacterString
    LIST_ATTRS_TO_INCLUDE = final_name final_value
    LIST_NAME = _attrs
    MODE = Attributes Only
    SEP = ,
    AGGREGATE -> ListExploder_2
ListExploder_2
    ATTR_ACCUM_MODE = Merge List Attributes
    ATTR_CONFLICT_RES = Use List Attribute Values
    LIST_ATTR = _attrs{}
    ELEMENTS -> AttributeCreator_2
AttributeCreator_2
    ATTR_TABLE = SET_TO @Value(final_name) = @Value(final_value)
    -> TestFilter
TestFilter
    DEFAULT_VALUE = <UNFILTERED>
    TEST_LIST = "BOOL_OP,OR,COMPOSITE_TEST,""""""1"""""",TEST_CLAUSE,TEST @Value(final_name) != _xml_source_",@Value(final_name) != _xml_source_
    @Value(final_name) != _xml_source_ -> ChangeDetector [REVISED]

Bookmark: Matched - Lists
StringConcatenator_2
    ACTION = Create New Attribute
    PARM_LINE = fme_basicstring:24%24:@Value(_matches{0}.part)@Value(_matches{2}.part)
    VAL_ATTR = _list_name
    -> AttributeRenamer_4
AttributeRenamer_4
    ATTR_TABLE = RENAME_SET_DEFAULT _attr_value > _list_value
    -> ListBuilder_2
ListBuilder_2
    GROUP_BY = _list_name fileIdentifier.CharacterString
    LIST_ATTRS_TO_INCLUDE = _list_value
    LIST_NAME = _values
    -> ListSorter_2
ListSorter_2
    ORDER = Ascending
    SRC_LIST = _values{}._list_value
    TYPE = Alphabetic
    -> ListConcatenator_2
ListConcatenator_2
    DROP_EMPTY_PARTS = No
    LIST_ATTR = _values{}._list_value
    SEP = |
    VAL_ATTR = final_value
    -> AttributeRenamer_5
AttributeRenamer_5
    ATTR_TABLE = RENAME_SET_DEFAULT _list_name > final_name
    -> Aggregator_3

Bookmark: Unmatch - Non-list Attributes
AttributeRenamer_6
    ATTR_TABLE:
      RENAME_SET_DEFAULT _attr_name > final_name
      RENAME_SET_DEFAULT _attr_value > final_value
    -> Aggregator_3
