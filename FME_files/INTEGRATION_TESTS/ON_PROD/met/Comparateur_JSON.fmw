FME workspace Comparateur_JSON.fmw

Parameters:
- ETALON_JSON = $(FME_MF_DIR)ETALON_DATA\PT_Harvester\BC\JSON_LOCAL\00a498df-f449-461d-a45e-c6e08a3df6a3.json
- RESULTAT_JSON = $(FME_MF_DIR)ETALON_DATA\PT_Harvester\BC\JSON_LOCAL\00a498df-f449-461d-a45e-c6e08a3df6a3.json
- KEYS_TO_IGNORE =   # KEYS_TO_IGNORE, list, comma-separated, like : metadata_modified, datetime, ...

PythonCaller
    NEW_ATTRIBUTES = _comparison_status _diff_details
    PYTHONSOURCE:
      import fme
      import fmeobjects
      import os
      import json

      class FeatureProcessor(object):
          """
          Reads two JSON files, compares them, and adds an attribute
          '_comparison_status' (PASSED/FAILED) to the feature.
          This version ignores specific keys.
          """

          def __init__(self):
              """Base constructor for class members."""
              super().__init__()
              self.log = fmeobjects.FMELogFile()
              self.diff_message = ""

          def has_support_for(self, support_type: int):
              """This method is called by FME to determine if the PythonCaller supports Bulk mode."""
              return support_type == fmeobjects.FME_SUPPORT_FEATURE_TABLE_SHIM

          def input(self, feature: fmeobjects.FMEFeature):
              """This method is called for each feature which enters the PythonCaller."""

              self.log.logMessageString("--- Python Script Started ---", fmeobjects.FME_INFORM)
              self.diff_message = "" # Reset diff message

              try:
                  # --- THIS SECTION IS UPDATED WITH YOUR NAMES ---
                  # 1. Get file paths and ignore list from FME Macro Values
                  json_file1_path = fme.macroValues['ETALON_JSON']
                  json_file2_path = fme.macroValues['RESULTAT_JSON']
                  ignore_keys_str = fme.macroValues['KEYS_TO_IGNORE']
                  # --- END OF UPDATED SECTION ---

                  self.log.logMessageString(f"File 1 Path: {json_file1_path}", fmeobjects.FME_INFORM)
                  self.log.logMessageString(f"File 2 Path: {json_file2_path}", fmeobjects.FME_INFORM)

                  # 2. Read and Print File 1
                  if os.path.exists(json_file1_path):
                      with open(json_file1_path, 'r', encoding='utf-8') as f1:
                          content1 = f1.read()
                      self.log.logMessageString(f"--- Content of File 1 (ETALON_JSON) ---", fmeobjects.FME_INFORM)
                      self.log.logMessageString(content1, fmeobjects.FME_INFORM)
                      self.log.logMessageString("--- End of File 1 ---", fmeobjects.FME_INFORM)
                  else:
                      self.log.logMessageString(f"ERROR: File 1 not found at {json_file1_path}", fmeobjects.FME_ERROR)

                  # 3. Read and Print File 2
                  if os.path.exists(json_file2_path):
                      with open(json_file2_path, 'r', encoding='utf-8') as f2:
                          content2 = f2.read()
                      self.log.logMessageString(f"--- Content of File 2 (RESULTAT_JSON) ---", fmeobjects.FME_INFORM)
                      self.log.logMessageString(content2, fmeobjects.FME_INFORM)
                      self.log.logMessageString("--- End of File 2 ---", fmeobjects.FME_INFORM)
                  else:
                      self.log.logMessageString(f"ERROR: File 2 not found at {json_file2_path}", fmeobjects.FME_ERROR)


                  # 4. Parse both JSON files
                  with open(json_file1_path, 'r', encoding='utf-8') as f1_parse:
                      data1 = json.load(f1_parse)

                  with open(json_file2_path, 'r', encoding='utf-8') as f2_parse:
                      data2 = json.load(f2_parse)

                  # 5. Prepare ignore list and remove keys
                  ignore_keys_list = [k.strip() for k in ignore_keys_str.split(',')] if ignore_keys_str else []

                  if ignore_keys_list:
                      self.log.logMessageString(f"Ignoring keys: {ignore_keys_list}", fmeobjects.FME_INFORM)

                      for key in ignore_keys_list:
                          if isinstance(data1, dict):
                              data1.pop(key, None)
                          if isinstance(data2, dict):
                              data2.pop(key, None)

                  # 6. Compare the modified JSON data
                  are_same = (data1 == data2)

                  # 7. Set status attribute based on result
                  if are_same:
                      self.log.logMessageString("--- Result: PASSED ---", fmeobjects.FME_INFORM)
                      feature.setAttribute('_comparison_status', 'PASSED')
                  else:
                      self.diff_message = "JSON files are not identical (after ignoring keys)."
                      self.log.logMessageString(f"--- Result: FAILED ---", fmeobjects.FME_WARN)
                      self.log.logMessageString(f"Difference Found: {self.diff_message}", fmeobjects.FME_WARN)
                      feature.setAttribute('_comparison_status', 'FAILED')
                      feature.setAttribute('_diff_details', self.diff_message)

                  # Send ALL features to the single 'PYOUTPUT' port
                  self.pyoutput(feature)


              except KeyError as e:
                  self.log.logMessageString(f"FATAL ERROR: Could not find FME parameter: {e}. Check Reader/Parameter names.", fmeobjects.FME_ERROR)
                  feature.setAttribute('_comparison_status', 'FAILED')
                  feature.setAttribute('_diff_details', f"Could not find FME parameter: {e}")
                  self.reject_feature(feature, "MISSING_PARAMETER", f"Could not find FME parameter: {e}")
                  return

              except json.JSONDecodeError as e:
                   self.log.logMessageString(f"FATAL ERROR: Error parsing JSON file: {e}", fmeobjects.FME_ERROR)
                   feature.setAttribute('_comparison_status', 'FAILED')
                   feature.setAttribute('_diff_details', f"Error parsing JSON file: {e}")
                   self.reject_feature(feature, "JSON_PARSE_ERROR", f"Error parsing JSON file: {e}")
                   return

              except Exception as e:
                  self.log.logMessageString(f"FATAL ERROR: {e}", fmeobjects.FME_ERROR)
                  feature.setAttribute('_comparison_status', 'FAILED')
                  feature.setAttribute('_diff_details', str(e))
                  self.reject_feature(feature, "PYTHON_EXCEPTION", str(e))
                  return

              self.log.logMessageString("--- Python Script Finished ---", fmeobjects.FME_INFORM)

          def close(self):
              """This method is called once all the FME Features have been processed from input()."""
              pass

          def process_group(self):
              """This method is called by FME for each group when group processing mode is enabled."""
              pass

          def reject_feature(self, feature: fmeobjects.FMEFeature, code: str, message: str):
              """This method can be used to output a feature to the <Rejected> port."""
              feature.setAttribute("fme_rejection_code", code)
              feature.setAttribute("fme_rejection_message", message)
              return
    PYTHONSYMBOL = FeatureProcessor
    -> TestFilter
TestFilter
    DEFAULT_VALUE = <UNFILTERED>
    TEST_LIST = "BOOL_OP,OR,COMPOSITE_TEST,""""""1"""""",TEST_CLAUSE,TEST @Value(_comparison_status) = PASSED",@Value(_comparison_status) = PASSED
    <UNFILTERED> -> Terminator
Terminator
    MESSAGE:
      HHHHHHHHHHHHHHHHHHHHHHHHHHHHHHHHHHHHHHHHHHHHHHHHHHHHHHHHHHHHHHHHHHHH
      H                               BEGIN                              H
      Translation Terminated
      2020: $(ETALON_JSON)
      2025: $(RESULTAT_JSON)
      Paths to ignore:
      $(KEYS_TO_IGNORE)

      @Value(_comparison_status)
      @Value(_diff_details)
      HHHHHHHHHHHHHHHHHHHHHHHHHHHHHHHHHHHHHHHHHHHHHHHHHHHHHHHHHHHHHHHHHHHH
      H                               END                                H
      HHHHHHHHHHHHHHHHHHHHHHHHHHHHHHHHHHHHHHHHHHHHHHHHHHHHHHHHHHHHHHHHHHHH

Bookmark: Comparateur_JSON_2020
Creator
    GEOMTYPE = Geometry Object
    NUM = 1
    CREATED -> ETALON_JSON_Flattener
    CREATED -> RESULTAT_JSON_Flattener
ETALON_JSON_Flattener: JSONFlattener
    ERROR_LIST_ATTR = _json_error
    FILEPATH_OR_URL = $(ETALON_JSON)
    READ_FROM_FILE = YES
    RECURSIVE = Yes
    -> AttributeExploder
AttributeExploder
    ATTR_NAME_LABEL = _attr_name
    ATTR_VALUE_LABEL = _attr_value
    EXPLODING_TYPE = Features
    KEEP_ATTRIBUTES = No
    KEEP_GEOMETRY = No
    LIST_NAME = _attr_list
    -> TestFilter_2
TestFilter_2
    DEFAULT_VALUE = <UNFILTERED>
    TEST_LIST = "BOOL_OP,OR,COMPOSITE_TEST,""""""1"""""",TEST_CLAUSE,CASE_INSENSITIVE_TEST @Value(_attr_name) CONTAINS _date_modified",@Value(_attr_name) CONTAINS _date_modified,"BOOL_OP,OR,COMPOSITE_TEST,""""""1"""""",TEST_CLAUSE,TEST @Value(_attr_name) = metadata_modified",@Value(_attr_name) = metadata_modified
    <UNFILTERED> -> TestFilter_3
AttributeCreator_5
    ATTR_TABLE = SET_TO _signature = @Value(_attr_name):@Value(_attr_value)
    -> ChangeDetector [ORIGINAL]
RESULTAT_JSON_Flattener: JSONFlattener
    ERROR_LIST_ATTR = _json_error
    FILEPATH_OR_URL = $(RESULTAT_JSON)
    READ_FROM_FILE = YES
    RECURSIVE = Yes
    -> AttributeExploder_2
AttributeExploder_2
    ATTR_NAME_LABEL = _attr_name
    ATTR_VALUE_LABEL = _attr_value
    EXPLODING_TYPE = Features
    KEEP_ATTRIBUTES = No
    KEEP_GEOMETRY = No
    LIST_NAME = _attr_list
    -> TestFilter_4
TestFilter_4
    DEFAULT_VALUE = <UNFILTERED>
    TEST_LIST = "BOOL_OP,OR,COMPOSITE_TEST,""""""1"""""",TEST_CLAUSE,CASE_INSENSITIVE_TEST @Value(_attr_name) CONTAINS _date_modified",@Value(_attr_name) CONTAINS _date_modified,"BOOL_OP,OR,COMPOSITE_TEST,""""""1"""""",TEST_CLAUSE,TEST @Value(_attr_name) = metadata_modified",@Value(_attr_name) = metadata_modified
    <UNFILTERED> -> TestFilter_5
AttributeCreator_6
    ATTR_TABLE = SET_TO _signature = @Value(_attr_name):@Value(_attr_value)
    -> ChangeDetector [REVISED]
ChangeDetector
    BLANK_AND_MISSING_DIFFER = No
    BLANK_AND_MISSING_NAMES_TRAITS_DIFFER = No
    CHECK_COORDINATE_SYSTEMS = No
    CHECK_TYPES_AND_ENCODINGS = No
    LENIENT_MATCH = No
    MATCH = FULL
    MATCH_STRATEGY = Match All Attributes
    UNCHANGED_OUTPUT = Output Original
    UPDATED -> ChangeDetector_Inserted
    INSERTED -> ChangeDetector_Inserted
    DELETED -> ChangeDetector_Inserted
ChangeDetector_Inserted: Logger
    LOG_FEATURE = LOG_RECORD
    MAXCOORDS = 20
    MAXFEATS = 20
    MESSAGE:
      HHHHHHHHHHHHHHHHHHHHHHHHHHHHHHHHHHHHHHHHHHHHHHHHHHHHHHHHHHHHHHHHHHHHHHH
      H                                                                   BEGIN                                                                                    H
      HHHHHHHHHHHHHHHHHHHHHHHHHHHHHHHHHHHHHHHHHHHHHHHHHHHHHHHHHHHHHHHHHHHHHHH
      -----------------------
      | @Value(_attr_name) |
      | @Value(_attr_value) |
      -----------------------
      HHHHHHHHHHHHHHHHHHHHHHHHHHHHHHHHHHHHHHHHHHHHHHHHHHHHHHHHHHHHHHHHHHHHHHH
      H                                                                   END                                                                                       H
      HHHHHHHHHHHHHHHHHHHHHHHHHHHHHHHHHHHHHHHHHHHHHHHHHHHHHHHHHHHHHHHHHHHHHHH
    SEVERITY = ERROR
    LOGGED -> ChangeDetector_Deleted
ChangeDetector_Deleted: Logger
    LOG_FEATURE = LOG_RECORD
    MAXCOORDS = 20
    MAXFEATS = 20
    MESSAGE:
      HHHHHHHHHHHHHHHHHHHHHHHHHHHHHHHHHHHHHHHHHHHHHHHHHHHHHHHHHHHHHHHHHHHHHHH
      H                                                                   BEGIN                                                                                    H
      HHHHHHHHHHHHHHHHHHHHHHHHHHHHHHHHHHHHHHHHHHHHHHHHHHHHHHHHHHHHHHHHHHHHHHH
      -----------------------
      | @Value(_attr_name) |
      | @Value(_attr_value) |
      -----------------------
      HHHHHHHHHHHHHHHHHHHHHHHHHHHHHHHHHHHHHHHHHHHHHHHHHHHHHHHHHHHHHHHHHHHHHHH
      H                                                                   END                                                                                       H
      HHHHHHHHHHHHHHHHHHHHHHHHHHHHHHHHHHHHHHHHHHHHHHHHHHHHHHHHHHHHHHHHHHHHHHH
    SEVERITY = INFO
    LOGGED -> FeatureHolder
FeatureHolder
    -> Terminator_2
Terminator_2
    MESSAGE:
      Translation Terminated. See logger.
      JSON has differences

Bookmark: Order_ETALON_JSON
TestFilter_3
    DEFAULT_VALUE = <UNFILTERED>
    TEST_LIST = "BOOL_OP,OR,COMPOSITE_TEST,""""""1"""""",TEST_CLAUSE,CASE_SENSITIVE_TEST @Value(_attr_name) CONTAINS_REGEX ^resources{\d+}",ListMember
    <UNFILTERED> -> AttributeCreator_5
    ListMember -> AttributeSplitter
AttributeSplitter
    ATTR_NAME = _attr_name
    DELIMITER = .
    DROP_EMPTY_PARTS = Yes
    LIST_NAME = _parts
    TRIM_OPTION = Both
    -> AttributeCreator
AttributeCreator
    ATTR_TABLE:
      SET_TO _list_group_id = @Value(_parts{0})
      SET_TO _list_attr_name = @Value(_parts{1})
    -> AttributeCreator_2
AttributeCreator_2
    ATTR_TABLE = SET_TO _key_value_pair = @Value(_list_attr_name):@Value(_attr_value)
    -> Sorter
Sorter
    SORT_PARM = _key_value_pair ALPHA ASCENDING
    SORTED -> Aggregator
Aggregator
    ACCUM_ATTRS_NAME = Drop Incoming Attributes
    AGGREGATE_TYPE = Homogeneous Collection (If Possible)
    CONCAT_ATTRS = _key_value_pair
    GROUP_BY = _list_group_id
    MODE = Geometry - Assemble One Level
    SEP = ;
    AGGREGATE -> AttributeManager
AttributeManager
    ATTR_TABLE:
      REMOVE _list_group_id
      RENAME_SET_VALUE _key_value_pair > _signature
    -> ChangeDetector [ORIGINAL]

Bookmark: Order_RESULTAT_JSON
TestFilter_5
    DEFAULT_VALUE = <UNFILTERED>
    TEST_LIST = "BOOL_OP,OR,COMPOSITE_TEST,""""""1"""""",TEST_CLAUSE,CASE_SENSITIVE_TEST @Value(_attr_name) CONTAINS_REGEX ^resources{\d+}",ListMember
    ListMember -> AttributeSplitter_2
    <UNFILTERED> -> AttributeCreator_6
AttributeSplitter_2
    ATTR_NAME = _attr_name
    DELIMITER = .
    DROP_EMPTY_PARTS = Yes
    LIST_NAME = _parts
    TRIM_OPTION = Both
    -> AttributeCreator_3
AttributeCreator_3
    ATTR_TABLE:
      SET_TO _list_group_id = @Value(_parts{0})
      SET_TO _list_attr_name = @Value(_parts{1})
    -> AttributeCreator_4
AttributeCreator_4
    ATTR_TABLE = SET_TO _key_value_pair = @Value(_list_attr_name):@Value(_attr_value)
    -> Sorter_2
Sorter_2
    SORT_PARM = _key_value_pair ALPHA ASCENDING
    SORTED -> Aggregator_2
Aggregator_2
    ACCUM_ATTRS_NAME = Drop Incoming Attributes
    AGGREGATE_TYPE = Homogeneous Collection (If Possible)
    CONCAT_ATTRS = _key_value_pair
    GROUP_BY = _list_group_id
    MODE = Geometry - Assemble One Level
    SEP = ;
    AGGREGATE -> AttributeManager_2
AttributeManager_2
    ATTR_TABLE:
      REMOVE _list_group_id
      RENAME_SET_VALUE _key_value_pair > _signature
    -> ChangeDetector [REVISED]
