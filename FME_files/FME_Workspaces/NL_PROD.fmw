FME workspace NL_PROD.fmw
Title: NL_PROD
Description: Description 
This workbench read and trasform all the metadata for the province of NewFoundLand & Labrador (NL)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P_T_ABBR: Two letter abbreviation code of the province or terrirtory (ex.: ON, QC, ...).
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
SAMPLE_SIZE: Number of features to process. Zero (0) means process all the features. A number n greater than 0 means sample or process only the first n features.
URL_VALIDATION : Indicates to validate or not created URL. (Should be Yes for prod)
VALIDATE_INSERT_PCT :Indicates to valide insert percentage. 75 % or less insert/update record  (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = NO
- IN_OUT_WORKING_DIR = $(FME_SHAREDRESOURCE_DATA)\PT_Harvester
- SAMPLE_SIZE = 0
- URL_VALIDATION = Yes
- VALIDATE_INSERT_PCT_JSON = Yes
- VALIDATE_INSERT_PCT_XML = Yes
- IN_CSV_LOOKUP_TABLES_DIR = $(IN_OUT_WORKING_DIR)\LOOKUP_TABLES   # DEFAULT_IN_CSV_LOOKUP_TABLES_DIR
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Flow Data Directory

Writers:
- XLSXW_1: XLSXW to $(OUT_XLS_NOTIFICATION_DIR)
- TEXTLINE_1: TEXTLINE to $(OUT_JSON_LOCAL_DIR)
- TEXTLINE_2: TEXTLINE to $(OUT_XML_PASSED_DIR)
- TEXTLINE_3: TEXTLINE to $(OUT_XML_FAILED_DIR)
- TEXTLINE_4: TEXTLINE to $(OUT_XML_LOCAL_DIR)

AttributeExposer
    ATTR_TABLE = title,
    -> UNIQUE_ID_CREATOR
Note: Create a UUID for each feature
UNIQUE_ID_CREATOR
    UNIQUE_ATT = @Value(title)
    -> EMPTY_FORMAT_MAPPER_NG [DATA_INPUT]
Note: When format is emty. Guess the format using the conent of the URL
EMPTY_FORMAT_MAPPER_NG
    CSV_FORMAT = Format
    CSV_MIME_TYPE = Mime_type
    IN_CSV_LOOKUP_TABLES_DIR = $(IN_CSV_LOOKUP_TABLES_DIR)
    P-T_ABBR = $(P-T_ABBR)
    URL_VALIDATION = $(URL_VALIDATION)
    DATA_OUTPUT -> AttributeExposer_3
    UNKNOWN_MIME_TYPE -> UNKNOWN_MIME_TYPE (writer XLSXW_1)
Junction
    -> METADATA_VALUE_MAPPER_NG_3 [DATA_INPUT]
Note: Writes XML to a local folder without publishing to PyCSW, and without the PyCSW transaction headers and footers
text_line (writer TEXTLINE_4)
    attributes: text_line_data buffer
Note: Writes XML published to the PyCSW to a local folder
text_line (writer TEXTLINE_2)
    attributes: text_line_data buffer
Note: Writes XML that failed to publish to the PyCSW to a local folder
text_line (writer TEXTLINE_3)
    attributes: text_line_data buffer
INVALI_METADATA (writer XLSXW_1)
    attributes: id string(200)
Junction_2
    -> ON_DATE_FORMATTER_2
text_line (writer TEXTLINE_1)
    attributes: text_line_data buffer
UNKNOWN_MIME_TYPE (writer XLSXW_1)
    attributes: id string(200), _unknown_mime_type string(200)
UNKNOWN_LICENCE (writer XLSXW_1)
    attributes: license_id string(200), id string(200)

Bookmark: Reading NL Datasets and creating attributes
Creator
    GEOMTYPE = Geometry Object
    NUM = 1
    CREATED -> Tester_3
Tester_3
    BOOL_OP = OR
    TEST_CLAUSE = TEST $(CATALOGUE_READER_SELECT) = Yes
    TEST_MODE = TEST
    PASSED -> NL_CATALOGUE_READER
    FAILED -> FeatureReader [INITIATOR]
Note: Read pre-recorded NL catalogue data
FeatureReader
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> ATTRIBUTE_VALUE_TEXT_CLEANER_2
    <REJECTED> -> Terminator
Terminator
    MESSAGE = Translation Terminated
Note: Read NL catalogue
NL_CATALOGUE_READER
    URL_DATASET_GEO = https://opendata.gov.nl.ca/public/opendata/page/?page-id=datasets-spatial
    URL_DATASET_NON_GEO = https://opendata.gov.nl.ca/public/opendata/page/?page-id=datasets-tabular
    URL_ROOT = https://opendata.gov.nl.ca
    -> ATTRIBUTE_VALUE_TEXT_CLEANER_2
    BROKEN_URL -> BROKEN_GEOHUB_URL (writer XLSXW_1)
Note: Clean all attribute from extra white spaces, \n, ...
ATTRIBUTE_VALUE_TEXT_CLEANER_2
    -> NL_ATTRIBUTE_EXTRACTOR
Note: Extract the metadata from the HTML tags
NL_ATTRIBUTE_EXTRACTOR
    -> DEFAULT_ATTRIBUTE_MAPPER_NG
Note: Sets default attribute values
DEFAULT_ATTRIBUTE_MAPPER_NG
    FEATURE_TYPE = Default_NL
    IN_CSV_LOOKUP_TABLES_DIR = $(IN_CSV_LOOKUP_TABLES_DIR)
    P-T_ABBR = $(P-T_ABBR)
    -> ATTRIBUTE_MANAGER_NG
Note: Manage missing attributes
ATTRIBUTE_MANAGER_NG
    IN_YAML_TEXT:
      notes:
          action: attribute_not_null
          attr2set: title
      org_contact.fr:
          action: attribute_not_null
          attr2set: org_contact.en
      data_collection_start_date:
          action: text_not_null
          attr2set: UNKNOWN
      record_last_modified:
          action: attribute_not_null
          attr2set: record_create_date
      record_publish_date:
          action: attribute_not_null
          attr2set: record_create_date
      license_id:
          action: text_not_null
          attr2set: License is missing
      resources{}.language:
          action: text_not_null
          attr2set: eng
      resources{}.protocol:
          action: text_not_null
          attr2set: HTTPS
      tags{}.display_name:
          action: attribute_not_null
          attr2set: default_tags
    -> AttributeExposer_5
AttributeExposer_5
    ATTR_TABLE = data_collection_start_date,
    -> EXTRACT_COLLECTION_START_END_DATE
Note: Set the collection start and end date
EXTRACT_COLLECTION_START_END_DATE
    CSV_PATH = $(IN_CSV_LOOKUP_TABLES_DIR)
    DATE_EXTENT = @Value(data_collection_start_date)
    FEATURE_TYPE = Manual_end_start_collection_date_NL
    PT = $(P-T_ABBR)
    -> AttributeExposer_7
    Unworking_extent -> UNWORKING_DATE_COLLECTION_EXTENT (writer XLSXW_1)
AttributeExposer_7
    ATTR_TABLE = license_id,
    -> LICENSE_FILTER_NG
Note: Only keep features with valid licenceopen licence
LICENSE_FILTER_NG
    FEATURE_TYPE = License_NL
    IN_CSV_LOOKUP_TABLES_DIR = $(IN_CSV_LOOKUP_TABLES_DIR)
    LICENSE_ATT = @Value(license_id)
    P-T_ABBR = $(P-T_ABBR)
    LICENSE_FILTER_PASSED -> AttributeExposer
    UNKNOWN_LICENSE -> UNKNOWN_LICENCE (writer XLSXW_1)
UNWORKING_DATE_COLLECTION_EXTENT (writer XLSXW_1)
    attributes: unmatched_date_extent string(200)
BROKEN_GEOHUB_URL (writer XLSXW_1)
    attributes: _url_dataset_geo string(200), _url_root string(200)

Bookmark: Add Geoportal Weblink
AttributeExposer_3
    ATTR_TABLE = resources{}.format,,id,
    -> AttributeExposer_18
AttributeExposer_18
    ATTR_TABLE = url_metadata,
    -> GEOPORTAL_WEBLINK_ADDER_NG
Note: Ajout du lien vers la métadonnées. Pout NL, on doit conserver URL_VALIDATION à No car les données ont déjà été lu dans le custom NL_CATALOGUE_READER. Il n'est donc pas nécessaire de les accéder de nouveau.
GEOPORTAL_WEBLINK_ADDER_NG
    FEATURE_TYPE = GeoportalWeblink_NL_en
    IN_CSV_LOOKUP_TABLES_DIR = $(IN_CSV_LOOKUP_TABLES_DIR)
    P-T_ABBR = $(P-T_ABBR)
    URL_VALIDATION = No
    WEBLINK_WILDCARD = @Value(url_metadata)
    -> GEO_NONE_GEO_SELECTOR

Bookmark: Spatail data filtering
Note: Filters geospatial data by referencing format, then by resources identified as having geographic markers
GEO_NONE_GEO_SELECTOR
    CSV_FILE_NAME = GeoSpatialValidation
    CSV_PATH = $(IN_CSV_LOOKUP_TABLES_DIR)
    CSV_PROVINCE = $(P-T_ABBR)
    YAML_DIRECTIVES:
      resources{}.format:
        domain: lookup_table_format
        spatial_type: overwrite
        not_found: log
        search_type: equals
    GEOSPATIAL -> SPATIAL_TYPE_MAPPER_NG [DATA_INPUT]
    NONE_GEOSPATIAL -> MANUAL_GEOSPATIAL_SETTER_NG [DATA_INPUT]
    LOG_ERROR -> GEOSPATIAL_FORMAT_NOT_MAPPED (writer XLSXW_1)
Note: Maps the spatial_representation_type of known geographic data, and geo data that could not be mapped to a specific spatial_representation_type is given value through lookup table where the type was researched manually
SPATIAL_TYPE_MAPPER_NG
    FEATURE_TYPE = UUID_Spatial_NL
    IN_CSV_LOOKUP_TABLES_DIR = $(IN_CSV_LOOKUP_TABLES_DIR)
    P-T_ABBR = $(P-T_ABBR)
    DATA_OUTPUT_FAILED -> AttributeExposer_10
    DATA_OUTPUT_PASSED -> Junction_3
AttributeExposer_10
    ATTR_TABLE = id,,title,,notes,
    -> SPATIAL_TYPE_NOT_MAPPED (writer XLSXW_1)
SPATIAL_TYPE_NOT_MAPPED (writer XLSXW_1)
    attributes: id auto(20)
GEOSPATIAL_FORMAT_NOT_MAPPED (writer XLSXW_1)
    attributes: id string(200), format string(200)
Note: Additional filtering step required for NL data. Items identified as NON-GEOSPATIAL in GEOSPATIAL_DATA_VALIDATOR were analyzed manually and a lookup table was created to identify non-filtered geo data and create the spatial_representation_type
MANUAL_GEOSPATIAL_SETTER_NG
    FEATURE_TYPE = UnmappedGeoData_NL
    IN_CSV_LOOKUP_TABLES_DIR = $(IN_CSV_LOOKUP_TABLES_DIR)
    P-T_ABBR = $(P-T_ABBR)
    GEOSPATIAL -> Junction_3
    NON-GEOSPATIAL -> Tester_2
    UNMAPPED_DATA -> UNMAPPED_GEODATA (writer XLSXW_1)
Junction_3
    -> Tester_7
UNMAPPED_GEODATA (writer XLSXW_1)
    attributes: id string(200), notes string(200), title string(200)

Bookmark: Activate Geo and Sample or full content
Tester_7
    BOOL_OP = OR
    TEST_CLAUSE = TEST @UpperCase($(ACTIVATE_GEO)) = YES
    TEST_MODE = TEST
    PASSED -> TestFilter
TestFilter
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction
    SAMPLES FEATURES -> Sampler_3
Sampler_3
    MODE = ORIGINAL
    RATE = $(SAMPLE_SIZE)
    SAMPLE_TYPE_MULTIPLIER = -1
    SAMPLE_MODE = No
    SAMPLE_TYPE_LONG = First N Features
    SAMPLED -> Junction

Bookmark: Attribute value mapper
Note: Map Role to HNAP standards
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
METADATA_VALUE_MAPPER_NG_3
    ATT_TO_MAP = contacts{}.role
    CODE_REFRESH = YES
    ENGLISH_REFRESH = YES
    ERROR_NOT_MAPPED = YES
    FEATURE_TYPE = Role
    FRENCH_REFRESH = YES
    IN_CSV_LOOKUP_TABLES_DIR = $(IN_CSV_LOOKUP_TABLES_DIR)
    P-T_ABBR = $(P-T_ABBR)
    -> METADATA_VALUE_MAPPER_NG_4 [DATA_INPUT]
Note: Maps update cycle to HNAP standards
METADATA_VALUE_MAPPER_NG_4
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_VALUE_MAPPER_NG_5 [DATA_INPUT]
Note: Maps progress code to HNAP standards
METADATA_VALUE_MAPPER_NG_5
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_6 [DATA_INPUT]
Note: Maps spatial rpresentation to HNAP standards
METADATA_VALUE_MAPPER_NG_6
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_VALUE_MAPPER_NG_7 [DATA_INPUT]
Note: Maps spatial_representation_type to HNAP standards8
METADATA_VALUE_MAPPER_NG_7
    ATT_TO_MAP = iso_topic
    CODE_REFRESH = NO
    ENGLISH_REFRESH = YES
    ERROR_NOT_MAPPED = YES
    FEATURE_TYPE = Topic
    FRENCH_REFRESH = NO
    IN_CSV_LOOKUP_TABLES_DIR = $(IN_CSV_LOOKUP_TABLES_DIR)
    P-T_ABBR = $(P-T_ABBR)
    -> METADATA_FORMAT_MAPPER_NG [DATA_INPUT]

Bookmark: Format value mapper
Note: This section utilizes the METADATA_FORMAT_MAPPER to correct data format values to valid data format values and to associate and add the French and English 'Resource Type' attribute to each data format type. It accesses a custom look up table applicable to data formats. / Turn the error mapping options and the data items to be mapped on or off by clicking on the transformer and selecting yes/no. / - ERROR_NOT_MAPPED: enables mapping of data item values that cannot be found in the lookup tables. / - REAL_VALUE_REFRESH: enables updating of data format attribute values. / - RES_TYPE_FR_REFRESH: enables mapping of French resource types. / - RES_TYPE_EN_REFRESH: enables mapping of English resource types. / Enter the attribute key name by clicking on the transformer and selecting the drop down menu next to the 'att_to_map' text box and selecting the 'Open text editor...' option. Explicitly enter the attribute key name in the text editor (ie: resources{}.format). / IMPORTANT: Do not select the 'Attribute Value' option from the drop down menu to select the attribute key name.
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_Geo (writer XLSXW_1)
    -> METADATA_VALUE_MAPPER_ERROR_MANAGER_2
UNKNOWN_MIME_TYPE_Geo (writer XLSXW_1)
    attributes: id string(200), _unknown_mime_type string(200)

Bookmark: Mapping error list creator
METADATA_VALUE_MAPPER_ERROR_MANAGER_2
    ERROR_OUTPUT -> METADATA_MAPPING_ERRORS_GEO (writer XLSXW_1)
    DATA_OUTPUT -> REMOVE_BROKEN_URL_WMS_ESRI_REST
METADATA_MAPPING_ERRORS_GEO (writer XLSXW_1)
    attributes: id string(200), error string(200)

Bookmark: Data cleanup. Dropping broken web services
Note: Tests WMS/ESRI_REST resource URL's and removes them where broken
REMOVE_BROKEN_URL_WMS_ESRI_REST
    URL_VALIDATION = $(URL_VALIDATION)
    -> WMS_REST_LANGUAGE_FORMATTER
    FAULTY_URL_OUTPUT -> MAP_SERVICE_URL_ERROR (writer XLSXW_1)
MAP_SERVICE_URL_ERROR (writer XLSXW_1)
    attributes: id auto(20), format string(8), url auto(20), _url_failure_message auto(20)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> RESOURCE_NAME_UNDERSCORE_REMOVER

Bookmark: Data preparation for metadata section
Note: Removes all underscores from resources{}.name attributes. Long compounded names joined by underscores in this field can cause display formatting issues when published to the FGP.
RESOURCE_NAME_UNDERSCORE_REMOVER
    DATA_OUTPUT -> AttributeExposer_13
AttributeExposer_13
    ATTR_TABLE = resources{},
    -> ListCopier
ListCopier
    DEST_LIST = distributionList
    SRC_LIST = resources{}
    -> GMD_SECTION_DATA_EXTRACTION
Note: Creates lists and removes duplicates for GMD_Section
GMD_SECTION_DATA_EXTRACTION
    -> AttributeCreator_2

Bookmark: New Bookmark
Note: Expose published parameter FORCED_PYCSW_URL
AttributeCreator_2
    ATTR_TABLE = SET_TO csw_url (varchar(200)) = $(FORCED_PYCSW_URL)
    -> ATTRIBUTE_MANAGER_NG_4
AttributeExposer_16
    ATTR_TABLE = search_criteria_pycsw,,csw_url,,record_last_modified,
    -> METADATA_DELTA_FINDER_GEN
METADATA_DELTA_FINDER_GEN
    ATTR_DATE_MODIFIED = record_last_modified
    CSW_FILTER = @Value(search_criteria_pycsw)
    LOCAL_SOURCE = $(LOCAL_SOURCE_METADATA_DELTA_FINDER)
    METADATA_OVERWRITE = $(METADATA_OVERWRITE)
    METADATA_TYPE = XML-HNAP
    SOURCE_DIRECTORY = $(OUT_XML_LOCAL_DIR)
    SOURCE_URL = @Value(csw_url)
    VALIDATE_INSERT_PCT = $(VALIDATE_INSERT_PCT_XML)
    YAML_FILE = $(IN_CSV_LOOKUP_TABLES_DIR)\$(P-T_ABBR)\metadata_delta_finder_$(P-T_ABBR)_geo.yaml
    Statistics -> StatisticsCalculator_Summary
    Update -> Junction_5
    Insert -> Junction_5
    Delete -> AttributeExposer_2
Note: Log statistics
StatisticsCalculator_Summary: Logger
    LOG_FEATURE = NONE
    MAXFEATS = 20
    MESSAGE:
      ************************
      **** Geo Unchanged Report ****
      ************************

      @Value(_real_count) features were unchanged

      ************************
      ************************
      ************************
    SEVERITY = INFO
AttributeExposer_2
    ATTR_TABLE = id,,title,
    -> DELETED_RECORDS_GEO (writer XLSXW_1)
DELETED_RECORDS_GEO (writer XLSXW_1)
    attributes: id string(200), title string(200)
Junction_5
    -> AWS_TRANSLATE

Bookmark: Listes Metadata_delta_finder
ATTRIBUTE_MANAGER_NG_4
    IN_YAML_TEXT:
      contacts{0}.p-t_entity:
         action: attribute_not_null
         attr2set: p-t_entity_en
      contacts{0}.p-t_entity_fr:
         action: attribute_not_null
         attr2set: p-t_entity_fr
      contacts{0}.sector:
         action: attribute_not_null
         attr2set: sector
      distributionList{0}.format_version:
         action: attribute_not_null
         attr2set: distribution_format_version
      iso_topic{0}.topic_value:
         action: attribute_not_null
         attr2set: iso_topic
      resources{0}.language:
         action: attribute_not_null
         attr2set: transfer_option_description_language
    -> ATTRIBUTE_MANAGER_NG_5
ATTRIBUTE_MANAGER_NG_5
    IN_YAML_TEXT:
      contacts{}.p-t_entity:
         action: attribute_not_null
         attr2set: p-t_entity_en
      contacts{}.p-t_entity_fr:
         action: attribute_not_null
         attr2set: p-t_entity_fr
      contacts{}.sector:
         action: attribute_not_null
         attr2set: sector
      distributionList{}.format_version:
         action: attribute_not_null
         attr2set: distribution_format_version
      iso_topic{}.topic_value:
         action: attribute_not_null
         attr2set: iso_topic
      resources{}.language:
         action: attribute_not_null
         attr2set: transfer_option_description_language
    -> AttributeExposer_16

Bookmark: Language Translation
Note: Translate some attributes using AWS translate
AWS_TRANSLATE
    ACTIVATE_TRANSLATION = $(ACTIVATE_TRANSLATION)
    ATTR_2_TRANSLATE = notes,title
    ATTR_LIST_2_TRANSLATE = tags{}.display_name,resources{}.name
    MODE = English-->French
    -> XML_PUBLISHER_NG
    TRANSLATION_PROBLEM -> AttributeExposer_8
AttributeExposer_8
    ATTR_TABLE = id,,title,
    -> TRANSLATION_PROBLEM_GEO (writer XLSXW_1)
TRANSLATION_PROBLEM_GEO (writer XLSXW_1)
    attributes: id string(200), title string(200), _translation_status string(200)

Bookmark: XML CREATION AND WRITING
Note: Excel config file to map NL attributes to those required by XML templates
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER_NG
    FEATURE_TYPE = Config_NL
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_4)
    INSERT_PASSED -> text_line (writer TEXTLINE_2)
    UPDATE_PASSED -> text_line (writer TEXTLINE_2)
    INSERT_FAILED -> text_line (writer TEXTLINE_3)
    InvalidMetadata -> INVALI_METADATA (writer XLSXW_1)
    UPDATE_FAILED -> text_line (writer TEXTLINE_3)

Bookmark: Activate None Geo and Sample or fulle content
Tester_2
    BOOL_OP = OR
    TEST_CLAUSE = TEST @UpperCase($(ACTIVATE_NON_GEO)) = YES
    TEST_MODE = TEST
    PASSED -> TestFilter_2
TestFilter_2
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_2
    SAMPLES FEATURES -> Sampler_4
Sampler_4
    MODE = ORIGINAL
    RATE = $(SAMPLE_SIZE)
    SAMPLE_TYPE_MULTIPLIER = -1
    SAMPLE_MODE = No
    SAMPLE_TYPE_LONG = First N Features
    SAMPLED -> Junction_2

Bookmark: Non-Geospatial Export
Note: Extracts, sorts, fitlers and creates data values and addresses areas where date values are missing
ON_DATE_FORMATTER_2
    -> RESOURCES_VALIDATOR_2
Note: Validates url, name and format on resources{} list items
RESOURCES_VALIDATOR_2
    -> METADATA_VALUE_MAPPER_NG_8 [DATA_INPUT]
Note: Adjusting update frequency value
METADATA_VALUE_MAPPER_NG_8
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> METADATA_FORMAT_MAPPER_NG_2 [DATA_INPUT]
Note: Format TBS
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_NoneGeo (writer XLSXW_1)
    -> AttributeExposer_9
Note: Extract errors created by the METADATA_VALUE_MAPPER_NG
METADATA_VALUE_MAPPER_ERROR_MANAGER
    ERROR_OUTPUT -> METADATA_MAPPING_ERRORS_NON_GEO (writer XLSXW_1)
    DATA_OUTPUT -> RESOURCE_NAME_UNDERSCORE_REMOVER_2
Note: Removes all underscores from resources{}.name attributes. Long compounded names joined by underscores in this field can cause display formatting issues when published to the FGP.
RESOURCE_NAME_UNDERSCORE_REMOVER_2
    DATA_OUTPUT -> AttributeExposer_6
AttributeExposer_6
    ATTR_TABLE = search_criteria_pycsw,,csw_url,,record_last_modified,,id,
    -> METADATA_DELTA_FINDER_GEN_2
METADATA_DELTA_FINDER_GEN_2
    ATTR_DATE_MODIFIED = record_last_modified
    LOCAL_SOURCE = Yes
    METADATA_OVERWRITE = $(METADATA_OVERWRITE)
    METADATA_TYPE = JSON-CKANExtCa
    SOURCE_DIRECTORY = $(OUT_JSON_LOCAL_DIR)
    VALIDATE_INSERT_PCT = $(VALIDATE_INSERT_PCT_JSON)
    YAML_FILE = $(IN_CSV_LOOKUP_TABLES_DIR)\$(P-T_ABBR)\metadata_delta_finder_$(P-T_ABBR)_non_geo.yaml
    Statistics -> StatisticsCalculator_Summary_2
    Update -> Junction_4
    Insert -> Junction_4
    Delete -> AttributeExposer_12
StatisticsCalculator_Summary_2: Logger
    LOG_FEATURE = NONE
    MAXFEATS = 20
    MESSAGE:
      ************************
      **** None Geo Unchanged Report ****
      ************************

      @Value(_real_count) features were unchanged

      ************************
      ************************
      ************************
    SEVERITY = INFO
AttributeExposer_12
    ATTR_TABLE = id,,title,
    -> DELETE_RECORDS_NON_GEO (writer XLSXW_1)
DELETE_RECORDS_NON_GEO (writer XLSXW_1)
    attributes: id auto(20), title auto(20)
Junction_4
    -> AWS_TRANSLATE_2
Note: Create a JSON document for each feature
JSON_PUBLISHER_NG
    FEATURE_TYPE = JSON_CONFIG_NL
    IN_CSV_LOOKUP_TABLES_DIR = $(IN_CSV_LOOKUP_TABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.display_name
    Keywords_FR = tags{}.display_name_fr
    P-T_ABBR = $(P-T_ABBR)
    Subject_LIST = TBS_Subject{}.value
    Topic_LIST = TBS_Topic{}.value
    OUTPUT_LOCAL -> AttributeExposer_4
AttributeExposer_4
    ATTR_TABLE = json_file,,id,
    -> AttributeCreator_6
AttributeCreator_6
    ATTR_TABLE = SET_TO text_line_data (varchar(200)) = @Value(json_file)
    -> text_line (writer TEXTLINE_1)
AttributeExposer_11
    ATTR_TABLE = id,,title,
    -> TRANSLATION_PROBLEMS_NONE_GEO (writer XLSXW_1)
TRANSLATION_PROBLEMS_NONE_GEO (writer XLSXW_1)
    attributes: id string(200), title string(200), _translation_status string(200)
METADATA_MAPPING_ERRORS_NON_GEO (writer XLSXW_1)
    attributes: id string(200), _element_index string(200), error string(200)
UNKNOWN_MIME_TYPE_NoneGeo (writer XLSXW_1)
    attributes: id string(200), _unknown_mime_type string(200)

Bookmark: Generating TBS_SUBJECT list based on tags
AttributeExposer_9
    ATTR_TABLE = resources{}.format_resourceType_en,,tags{},,tags{}.display_name,
    -> ListCopier_2
Note: Copy tags in a temp list
ListCopier_2
    DEST_LIST = TBS_Subject
    SRC_LIST = tags{}
    -> ListRenamer
ListRenamer
    LEAVE_ORIG = No
    LIST_ACTION = Rename
    LIST_COMPONENT_NAMES = TBS_Subject{},TBS_Subject{},display_name,value
    LIST_NAME = TBS_Subject{}.display_name
    -> METADATA_VALUE_MAPPER_NG_9 [DATA_INPUT]
Note: Subject TBS
METADATA_VALUE_MAPPER_NG_9
    ATT_TO_MAP = TBS_Subject{}.value
    CODE_REFRESH = NO
    ENGLISH_REFRESH = YES
    ERROR_NOT_MAPPED = YES
    FEATURE_TYPE = Subject_TBS_NL
    FRENCH_REFRESH = NO
    IN_CSV_LOOKUP_TABLES_DIR = $(IN_CSV_LOOKUP_TABLES_DIR)
    P-T_ABBR = $(P-T_ABBR)
    -> AttributeExposer_14
AttributeExposer_14
    ATTR_TABLE = TBS_Subject{}.value,
    -> ListDuplicateRemover
Note: Removeing duplicates on subject value
ListDuplicateRemover
    SRC_LIST = TBS_Subject{}.value
    -> AttributeExposer_20

Bookmark: Generating Tbs Topic based on tags
AttributeExposer_20
    ATTR_TABLE = extracted_topic{}.value,,tags{},,tags{}.display_name,
    -> ListCopier_3
ListCopier_3
    DEST_LIST = TBS_Topic
    SRC_LIST = tags{}
    -> ListRenamer_2
ListRenamer_2
    LEAVE_ORIG = No
    LIST_ACTION = Rename
    LIST_COMPONENT_NAMES = TBS_Topic{},TBS_Topic{},display_name,value
    LIST_NAME = TBS_Topic{}.display_name
    -> METADATA_VALUE_MAPPER_NG_10 [DATA_INPUT]
Note: Topic TBS
METADATA_VALUE_MAPPER_NG_10
    ATT_TO_MAP = TBS_Topic{}.value
    CODE_REFRESH = NO
    ENGLISH_REFRESH = YES
    ERROR_NOT_MAPPED = YES
    FEATURE_TYPE = Topic_TBS_NL
    FRENCH_REFRESH = NO
    IN_CSV_LOOKUP_TABLES_DIR = $(IN_CSV_LOOKUP_TABLES_DIR)
    P-T_ABBR = $(P-T_ABBR)
    -> AttributeExposer_15
AttributeExposer_15
    ATTR_TABLE = TBS_Topic{}.value,
    -> ListDuplicateRemover_2
ListDuplicateRemover_2
    SRC_LIST = TBS_Topic{}.value
    -> METADATA_VALUE_MAPPER_ERROR_MANAGER

Bookmark: Language translation
Note: Translate some attributes using AWS translate
AWS_TRANSLATE_2
    ACTIVATE_TRANSLATION = $(ACTIVATE_TRANSLATION)
    ATTR_2_TRANSLATE = notes,title
    ATTR_LIST_2_TRANSLATE = tags{}.display_name,resources{}.name
    MODE = English-->French
    -> JSON_PUBLISHER_NG
    TRANSLATION_PROBLEM -> AttributeExposer_11

FME custom transformer ON_TopicExtractor

Parameters:
- DEFAULT_TOPIC =

Topic (input)
    -> AttributeExposer_2
AttributeExposer_2
    ATTR_LIST = original_value
    -> AttributeCreator
AttributeCreator
    ATTR_TABLE:
      SET_TO _odre = 1
      SET_TO topic = @Value(original_value)
    -> Sorter
Input (input)
    -> AttributeExposer
AttributeExposer
    ATTR_LIST = keywords.en{}
    -> AttributeCreator_2
AttributeCreator_2
    ATTR_TABLE:
      SET_TO _odre = 2
      SET_TO DEFAULT_TOPIC = $(DEFAULT_TOPIC)
    -> Sorter
Sorter
    SORT_PARM = _odre NUMERIC ASCENDING
    SORTED -> PythonCaller
PythonCaller
    PYTHONSOURCE:
      import fme
      import fmeobjects
      # Template Function interface:
      # When using this function, make sure its name is set as the value of
      # the 'Class or Function to Process Features' transformer parameter


      # Template Class Interface:
      # When using this class, make sure its name is set as the value of
      # the 'Class or Function to Process Features' transformer parameter
      class FeatureProcessor(object):
          def __init__(self):
              self.topic=[]

          def input(self,feature):
              if int(feature.getAttribute('_odre'))==1:
                  #Ajouter le topic à la liste
                  self.topic.append(feature.getAttribute('topic'))

              else:

                 #Extraire le topic des keywords
                 extracted_topic=[feature.getAttribute('DEFAULT_TOPIC')]
                 feature_keywords=feature.getAttribute('keywords.en{}')

                 real_topic=False

                 for topics in self.topic:

                     if topics in feature_keywords:

                         if not real_topic:
                             #Reset de la liste pour vraie valeur
                             extracted_topic=[]
                             real_topic=True

                         extracted_topic.append(topics)

                 feature.setAttribute('extracted_topic{}.value',extracted_topic)




                 self.pyoutput(feature)
          def close(self):
              pass
    PYTHONSYMBOL = FeatureProcessor
    -> AttributeRemover
AttributeRemover
    REMOVE_ATTRS = _odre,DEFAULT_TOPIC
    -> ATTRIBUTE_UNEXPOSER
ATTRIBUTE_UNEXPOSER
    -> Output (output)
Output (output)
