FME workspace AB_PROD.fmw
Title: AB_PROD
Description: Description 
This workbench read and trasform all the metadata for the province of Alberta (AB)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
SAMPLE_SIZE: Number of features to process. Zero (0) means process all the features. A number n greater than 0 means sample or process only the first n features.
URL_VALIDATION : Indicates to validate or not created URL. (Should be Yes for prod)
VALIDATE_INSERT_PCT :Indicates to valide insert percentage. 75 % or less insert/update record  (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = NO
- SAMPLE_SIZE = 0
- IN_OUT_WORKING_DIR = $(FME_SHAREDRESOURCE_DATA)\PT_Harvester
- URL_VALIDATION = Yes
- VALIDATE_INSERT_PCT_JSON = Yes
- VALIDATE_INSERT_PCT_XML = Yes
- IN_CSV_LOOKUP_TABLES_DIR = $(IN_OUT_WORKING_DIR)\LOOKUP_TABLES
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\AB_FGP_XML_BUILDER.log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_LOCAL_DIR = $(IN_OUT_WORKING_DIR)\$(P-T_ABBR)\XML_LOCAL
- OUT_XML_FAILED_DIR = $(IN_OUT_WORKING_DIR)\$(P-T_ABBR)\XML_FAILED
- OUT_XML_PASSED_DIR = $(IN_OUT_WORKING_DIR)\$(P-T_ABBR)\XML_PASSED
- FME_SHAREDRESOURCE_DATA = C:\Data   # FME Flow Data Directory

Writers:
- TEXTLINE_1: TEXTLINE to $(OUT_XML_FAILED_DIR)
- TEXTLINE_2: TEXTLINE to $(OUT_XML_LOCAL_DIR)
- TEXTLINE_3: TEXTLINE to $(OUT_XML_PASSED_DIR)
- XLSXW_1: XLSXW to $(OUT_XLS_NOTIFICATION_DIR)
- TEXTLINE_4: TEXTLINE to $(OUT_JSON_LOCAL_DIR)

Junction_3
    -> AttributeExposer_9
Junction_4
    -> METADATA_VALUE_MAPPER_NG_10 [DATA_INPUT]

Bookmark: Reading AB Geoportal datasets
Creator_2
    GEOMTYPE = Geometry Object
    NUM = 1
    CREATED -> Tester_3
Tester_3
    BOOL_OP = OR
    TEST_CLAUSE = TEST $(CATALOGUE_READER_SELECT) = Yes
    TEST_MODE = TEST
    PASSED -> Catalogue_Reader
    FAILED -> FeatureReader [INITIATOR]
GEODISCOVER_BROKEN_URL (writer XLSXW_1)
    attributes: url_xml auto(20), id auto(20)
FeatureReader
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> AttributeExposer_2
LICENSE_FILTER_NG
    FEATURE_TYPE = License_AB
    IN_CSV_LOOKUP_TABLES_DIR = $(IN_CSV_LOOKUP_TABLES_DIR)
    LICENSE_ATT = @Value(license_id)
    P-T_ABBR = $(P-T_ABBR)
    LICENSE_FILTER_PASSED -> ATTRIBUTE_VALUE_TEXT_CLEANER
    UNKNOWN_LICENSE -> UNKNOWN_LICENCE (writer XLSXW_1)
UNKNOWN_LICENCE (writer XLSXW_1)
    attributes: license_id auto(20), id string(37)

Bookmark: Extracting data from AB portal
Note: Filter done on CKAN_FILTER (fq=type:opendata)
Catalogue_Reader: Catalogue Reader
    CKAN_FILTER = fq=type:opendata
    CUSTOM_CSW_LIST_NAME = DefaultNoList{}
    CUSTOM_URL = https://open.alberta.ca/api/3/action
    SOURCE_URL = Manuel
    Résultats -> AB_GEODISCOVER_RESOURCE_EXTRACTOR
AB_GEODISCOVER_RESOURCE_EXTRACTOR
    UNWORKING_URL -> GEODISCOVER_BROKEN_URL (writer XLSXW_1)
    -> AttributeExposer_2

Bookmark: Remove data from Statistics Canada
AttributeExposer_2
    ATTR_TABLE = license_id,,tags{},,notes,,organisation.name,
    -> Tester_6
Tester_6
    BOOL_OP = OR
    TEST_CLAUSE:
      CASE_INSENSITIVE_TEST @Value(notes) CONTAINS StatCan Product
      CASE_INSENSITIVE_TEST @Value(organisation.name) CONTAINS Treasury Board and Finance
    TEST_MODE = CASE_INSENSITIVE_TEST
    FAILED -> LICENSE_FILTER_NG

Bookmark: Manage attributes
ATTRIBUTE_VALUE_TEXT_CLEANER
    -> DEFAULT_ATTRIBUTE_MAPPER_NG
DEFAULT_ATTRIBUTE_MAPPER_NG
    FEATURE_TYPE = Default_AB
    IN_CSV_LOOKUP_TABLES_DIR = $(IN_CSV_LOOKUP_TABLES_DIR)
    P-T_ABBR = $(P-T_ABBR)
    -> PythonCaller
Note: Change topic{} list to / iso_topic{}.topic_value listattribute
PythonCaller
    PYTHONSOURCE:
      import fme
      import fmeobjects
      from Python.FME_utils import FME_utils

      # Template Function interface:
      # When using this function, make sure its name is set as the value of
      # the 'Class or Function to Process Features' transformer parameter
      def FeatureProcessor(feature):

          max_index=FME_utils.max_index_attribute_list(feature,'topic{}')
          for j in range(max_index+1):
              feature.setAttribute('iso_topic{%i}.topic_value'%(j),feature.getAttribute('topic{%i}'%(j)))
    PYTHONSYMBOL = FeatureProcessor
    -> ATTRIBUTE_MANAGER_NG_2
ATTRIBUTE_MANAGER_NG_2
    IN_YAML_TEXT:
      data_collection_start_date:
           action: attribute_overwrite
           attr2set: time_coverage_from

      data_collection_end_date:
           action: attribute_overwrite
           attr2set: time_coverage_to

      record_create_date:
           action: attribute_overwrite
           attr2set: date_created

      record_last_modified:
           action: attribute_overwrite
           attr2set: metadata_modified

      record_publish_date:
           action: attribute_overwrite
           attr2set: date_issued

      sector:
           action: attribute_overwrite
           attr2set: organization.title

      resource_update_cycle:
           action: attribute_overwrite
           attr2set: updatefrequency

      contacts{0}.name:
           action: attribute_overwrite
           attr2set: contact

      contacts{0}.email:
           action: attribute_overwrite
           attr2set: contact_email
    -> ATTRIBUTE_MANAGER_NG
ATTRIBUTE_MANAGER_NG
    IN_YAML_TEXT:
      contacts{0}.name:
         action: attribute_not_null
         attr2set: default_contact_name

      contacts{0}.email:
         action: attribute_not_null
         attr2set: default_contact_email

      tags{0}.display_name:
          action: attribute_not_null
          attr2set: default_tag_value

      iso_topic{0}.topic_value:
           action: attribute_not_null
           attr2set: default_topic_value

      data_collection_start_date:
           action: attribute_not_null
           attr2set: defaut_data_collection_start_date

      resource_update_cycle:
           action: attribute_not_null
           attr2set: default_update_frequency

      record_publish_date:
           action: attribute_not_null
           attr2set: record_create_date

      record_last_modified:
           action: attribute_not_null
           attr2set: record_create_date
    -> AttributeExposer_11

Bookmark: Manage date format
AttributeExposer_11
    ATTR_TABLE = record_create_date,,record_publish_date,,record_last_modified,,data_collection_start_date,,data_collection_end_date,,id,
    -> AttributeManager
AttributeManager
    ATTR_TABLE:
      SET_TO record_create_date (varchar(200)) = @DateTimeParse(@Value(record_create_date),%Y-%m-%d)
      SET_TO record_publish_date (varchar(200)) = @DateTimeParse(@Value(record_publish_date),%Y-%m-%d)
      SET_TO record_last_modified (varchar(200)) = @DateTimeParse(@Value(record_last_modified),%Y-%m-%d)
      SET_TO data_collection_start_date (varchar(200)) = @DateTimeParse(@Value(data_collection_start_date),%Y-%m-%d)
      SET_TO data_collection_end_date (varchar(200)) = @DateTimeParse(@Value(data_collection_end_date),%Y-%m-%d)
    -> DateTimeConverter
Note: Converts time attributes to ISO yyyy-dd-mm format
DateTimeConverter
    DATETIME_ATTR = data_collection_end_date record_create_date record_publish_date record_last_modified data_collection_start_date
    OUT_FORMAT = %Y-%m-%d
    PASSTHROUGH = YES
    REPAIR_INPUT = YES
    -> PythonCaller_6
    <REJECTED> -> WRONG_FORMAT_DATE (writer XLSXW_1)
Note: If there are some metadata with problems in their date format; add a CT with a LUT if issue cannot be solved in the attribute manager
WRONG_FORMAT_DATE (writer XLSXW_1)
    attributes: id auto(20)

Bookmark: format mapper
Note: If resource{}.url contains WMSServer?; add request=GetCapabilities&service=WMS at the end or the url
PythonCaller_6
    PYTHONSOURCE:
      import fme
      import fmeobjects
      from Python.FME_utils import FME_utils

      #def processFeature(feature):
      #    pass

      # Template Class Interface:
      # When using this class, make sure its name is set as the value of
      # the 'Class or Function to Process Features' transformer parameter
      def FeatureProcessor(feature):

          max_index=FME_utils.max_index_attribute_list(feature,'resources{}.url')
          for j in range(max_index+1):
              x = feature.getAttribute('resources{%i}.url'%(j))
              if x:
               if x.endswith('WMSServer?') :
                feature.setAttribute('resources{%i}.url'%(j),x+'request=GetCapabilities&service=WMS')
               elif x.endswith('WMSServer'):
                feature.setAttribute('resources{%i}.url'%(j),x+'?request=GetCapabilities&service=WMS')
    PYTHONSYMBOL = FeatureProcessor
    -> PythonCaller_2
Note: If format = WMS or EsriRest; remove format value so that it is added in empty format mapper ng; to ensure that only valid WMS or EsriRest format are added
PythonCaller_2
    PYTHONSOURCE:
      import fme
      import fmeobjects
      from Python.FME_utils import FME_utils

      #def processFeature(feature):
      #    pass

      # Template Class Interface:
      # When using this class, make sure its name is set as the value of
      # the 'Class or Function to Process Features' transformer parameter
      def FeatureProcessor(feature):

          max_index=FME_utils.max_index_attribute_list(feature,'resources{}.format')
          for j in range(max_index+1):
              x = feature.getAttribute('resources{%i}.format'%(j))
              url = feature.getAttribute('resources{%i}.url'%(j))

              if url:
                  if url.endswith('service=WMS') or url.endswith('MapServer') or url.endswith('MapServer/WMS') or url.endswith('MapServer/') or url.endswith('WMS')or url.endswith('FeatureServer'):
                      feature.setAttributeNullWithType('resources{%i}.format'%(j),fmeobjects.FME_ATTR_ENCODED_STRING)

              elif x:
                  if x.upper() == 'ESRI REST' or x.upper() == 'WMS' :
                      feature.setAttributeNullWithType('resources{%i}.format'%(j),fmeobjects.FME_ATTR_ENCODED_STRING)
    PYTHONSYMBOL = FeatureProcessor
    -> EMPTY_FORMAT_MAPPER_NG [DATA_INPUT]
EMPTY_FORMAT_MAPPER_NG
    CSV_FORMAT = Format
    CSV_MIME_TYPE = Mime_type
    IN_CSV_LOOKUP_TABLES_DIR = $(IN_CSV_LOOKUP_TABLES_DIR)
    P-T_ABBR = $(P-T_ABBR)
    URL_VALIDATION = $(URL_VALIDATION)
    DATA_OUTPUT -> FORMAT_VALIDATOR
    UNKNOWN_MIME_TYPE -> UNKNOWN_MIME_TYPE (writer XLSXW_1)
FORMAT_VALIDATOR
    -> AttributeExposer_4
UNKNOWN_MIME_TYPE (writer XLSXW_1)
    attributes: _unknown_mime_type string(8), _url_validation string(8), id string(8)

Bookmark: Email format
AttributeExposer_4
    ATTR_TABLE = default_contact_email,
    -> EMAIL_FORMAT_TESTER
EMAIL_FORMAT_TESTER
    DEFAULT_CONTACT_EMAIL = @Value(default_contact_email)
    -> METADATA_VALUE_MAPPER_NG_8 [DATA_INPUT]
METADATA_VALUE_MAPPER_NG_8
    ATT_TO_MAP = contacts{}.email
    CODE_REFRESH = NO
    ENGLISH_REFRESH = YES
    ERROR_NOT_MAPPED = NO
    FEATURE_TYPE = Email
    FRENCH_REFRESH = NO
    IN_CSV_LOOKUP_TABLES_DIR = $(IN_CSV_LOOKUP_TABLES_DIR)
    P-T_ABBR = $(P-T_ABBR)
    -> PythonCaller_4

Bookmark: manage resources name and url
Note: URL trimmer / or ?
PythonCaller_4
    PYTHONSOURCE:
      import fme
      import fmeobjects
      from Python.FME_utils import FME_utils

      # Template Function interface:
      # When using this function, make sure its name is set as the value of
      # the 'Class or Function to Process Features' transformer parameter
      def processFeature(feature):

          max_index=FME_utils.max_index_attribute_list(feature,'resources{}')
          for i in range(max_index+1):
              url=feature.getAttribute('resources{%d}.url'%(i))

              #Removing ? at the end
              url=url.rstrip(r'?')

              #Remover / at the
              url=url.rstrip(r'/')


              feature.setAttribute('resources{%d}.url'%(i),url)
    PYTHONSYMBOL = processFeature
    -> PythonCaller_3
Note: Ressources name extraction based on file name
PythonCaller_3
    PYTHONSOURCE:
      import fme
      import fmeobjects
      import os
      from Python.FME_utils import FME_utils

      # Template Function interface:
      # When using this function, make sure its name is set as the value of
      # the 'Class or Function to Process Features' transformer parameter
      def processFeature(feature):

          max_index=FME_utils.max_index_attribute_list(feature,'resources{}')
          for i in range(max_index+1):
              url=feature.getAttribute('resources{%d}.url'%(i))

              #Get file name from URL
              if not feature.getAttribute('resources{%d}.name'%(i)):
                  name=os.path.basename(url)
                  feature.setAttribute('resources{%d}.name'%(i),name)
    PYTHONSYMBOL = processFeature
    -> AttributeExposer_6

Bookmark: resources extraction and validation
AttributeExposer_6
    ATTR_TABLE = id,
    -> GEOPORTAL_WEBLINK_ADDER_NG
Note: On ne valide pas l'URL. / Trop long pour rien et vu que les métadonnées viennent de CKAN, le risque est faible.
GEOPORTAL_WEBLINK_ADDER_NG
    FEATURE_TYPE = GeoportalWeblink_AB
    IN_CSV_LOOKUP_TABLES_DIR = $(IN_CSV_LOOKUP_TABLES_DIR)
    P-T_ABBR = $(P-T_ABBR)
    URL_VALIDATION = No
    WEBLINK_WILDCARD = @Value(id)
    -> PythonCaller_5
RESOURCES_VALIDATOR
    -> URL_HTTPS_MAKER [UUIDGenerator_Input]
URL_HTTPS_MAKER
    P-T_ABBR = $(P-T_ABBR)
    URL_VALIDATION = $(URL_VALIDATION)
    -> GEO_NONE_GEO_SELECTOR
UNKNOWN_RESSOURCE_LANGUAGE (writer XLSXW_1)
    attributes: url auto(20), id auto(20)

Bookmark: manage resources language
Note: Add resources{}.language and put default value to "english"
PythonCaller_5
    PYTHONSOURCE:
      import fme
      import fmeobjects
      from Python.FME_utils import FME_utils

      # Template Function interface:
      # When using this function, make sure its name is set as the value of
      # the 'Class or Function to Process Features' transformer parameter
      def FeatureProcessor(feature):

          max_index=FME_utils.max_index_attribute_list(feature,'resources{}')
          for j in range(max_index+1):
              feature.setAttribute('resources{%i}.language'%(j),"english")
    PYTHONSYMBOL = FeatureProcessor
    -> AB_language_manager
Note: Possible values for AB_resources_language: / english; french; english_and_french
Note: change resources{}.language value base on a look-up table (AB_resources_language)
AB_language_manager
    IN_CSV_LOOKUP_TABLES_DIR = $(IN_CSV_LOOKUP_TABLES_DIR)
    P-T_ABBR = $(P-T_ABBR)
    feature_type = AB_resources_language
    res_url_unknown_language -> UNKNOWN_RESSOURCE_LANGUAGE (writer XLSXW_1)
    -> RESOURCES_VALIDATOR

Bookmark: Geo non-geo selector
GEO_NONE_GEO_SELECTOR
    CSV_FILE_NAME = GeoSpatialValidation
    CSV_PATH = $(IN_CSV_LOOKUP_TABLES_DIR)
    CSV_PROVINCE = $(P-T_ABBR)
    YAML_DIRECTIVES:
      resources{}.format:
        domain: lookup_table_format
        spatial_type: overwrite
        not_found: log
        search_type: equals
      #
      title:
        domain: ['(GIS data)<pipe>(Image data[,]\sTiff\sformat)']
        spatial_type: no_overwrite
        not_found: no_log
        search_type: contains_regex
    GEOSPATIAL -> SPATIAL_TYPE_MAPPER_NG [DATA_INPUT]
    NONE_GEOSPATIAL -> MANUAL_GEOSPATIAL_SETTER_NG [DATA_INPUT]
    LOG_ERROR -> GEOSPATIAL_FORMAT_NOT_MAPPED (writer XLSXW_1)
Note: For now, there are no need to use a lookuptable. All features have a spatial type based on format
SPATIAL_TYPE_MAPPER_NG
    IN_CSV_LOOKUP_TABLES_DIR = $(IN_CSV_LOOKUP_TABLES_DIR)
    P-T_ABBR = $(P-T_ABBR)
    DATA_OUTPUT_FAILED -> AttributeExposer_18
    DATA_OUTPUT_PASSED -> TestFilter_3
AttributeExposer_18
    ATTR_TABLE = id,,title,,notes,
    -> SPATIAL_TYPE_NOT_MAPPED (writer XLSXW_1)
SPATIAL_TYPE_NOT_MAPPED (writer XLSXW_1)
    attributes: id string(200), title string(200), notes string(200)
GEOSPATIAL_FORMAT_NOT_MAPPED (writer XLSXW_1)
    attributes: format string(8), id string(8)
MANUAL_GEOSPATIAL_SETTER_NG
    FEATURE_TYPE = UnmappedGeoData_AB
    IN_CSV_LOOKUP_TABLES_DIR = $(IN_CSV_LOOKUP_TABLES_DIR)
    P-T_ABBR = $(P-T_ABBR)
    GEOSPATIAL -> TestFilter_3
    NON-GEOSPATIAL -> TestFilter_4
    UNMAPPED_DATA -> UNMAPPED_DATA (writer XLSXW_1)
TestFilter_3
    DEFAULT_VALUE = <UNFILTERED>
    PASSED_TEST_GROUP_OUTPUT = FIRST
    TEST_LIST = "BOOL_OP,OR,COMPOSITE_TEST,""""""1"""""",TEST_CLAUSE,CASE_INSENSITIVE_TEST $(ACTIVATE_GEO) = yes",ACTIVATE_GEO
    ACTIVATE_GEO -> TestFilter
TestFilter_4
    DEFAULT_VALUE = <UNFILTERED>
    PASSED_TEST_GROUP_OUTPUT = FIRST
    TEST_LIST = "BOOL_OP,OR,COMPOSITE_TEST,""""""1"""""",TEST_CLAUSE,CASE_INSENSITIVE_TEST $(ACTIVATE_NON_GEO) = yes",ACTIVATE_NON_GEO
    ACTIVATE_NON_GEO -> TestFilter_2
UNMAPPED_DATA (writer XLSXW_1)
    attributes: notes auto(20), title auto(20), id auto(20)

Bookmark: Samples or full content
TestFilter
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_3
    SAMPLES FEATURES -> Sampler_2
Sampler_2
    MODE = ORIGINAL
    RATE = $(SAMPLE_SIZE)
    SAMPLE_TYPE_MULTIPLIER = -1
    SAMPLE_MODE = No
    SAMPLE_TYPE_LONG = First N Features
    SAMPLED -> Junction_3

Bookmark: Manage Geo Extent
AttributeExposer_9
    ATTR_TABLE = spatialcoverage1,
    -> Tester
Note: test if spatialcoverage1 contains letters (text) instead of coordinates
Tester
    BOOL_OP = OR
    TEST_CLAUSE = CASE_INSENSITIVE_TEST @Value(spatialcoverage1) CONTAINS_REGEX [a-z]
    TEST_MODE = CASE_INSENSITIVE_TEST
    PASSED -> Spatial_extent_validator
    FAILED -> AttributeSplitter
Note: Split the coordinates into 4 attributes for the extent
AttributeSplitter
    ATTR_NAME = spatialcoverage1
    DELIMITER = ,
    DROP_EMPTY_PARTS = NO
    LIST_NAME = geoextent_list
    TRIM_TYPE = BOTH
    -> AttributeRenamer_2
AttributeRenamer_2
    ATTR_TABLE:
      RENAME_SET_DEFAULT geoextent_list{0} > west_bound_longitude
      RENAME_SET_DEFAULT geoextent_list{1} > north_bound_latitude
      RENAME_SET_DEFAULT geoextent_list{2} > east_bound_longitude
      RENAME_SET_DEFAULT geoextent_list{3} > south_bound_latitude
    KEEP_RENAMED_ONLY = no
    MISSING_INPUT_ATTRS = PRESERVE
    -> Spatial_extent_validator
Spatial_extent_validator
    FEATURE_TYPE = SpatialExtent_AB
    IN_CSV_LOOKUPTABLES_DIR = $(IN_CSV_LOOKUP_TABLES_DIR)
    P-T_ABBR = $(P-T_ABBR)
    default_east_long = defaut_east_bound_longitude
    default_north_lat = defaut_north_bound_latitude
    default_south_lat = defaut_south_bound_latitude
    default_west_long = defaut_west_bound_longitude
    east_longitude = east_bound_longitude
    north_latitude = north_bound_latitude
    south_latitude = south_bound_latitude
    west_longitude = west_bound_longitude
    -> ATTRIBUTE_MANAGER_NG_3
    EXTENT_TO_VALIDATE -> UNKNOWN_SPATIAL_EXTENT (writer XLSXW_1)
ATTRIBUTE_MANAGER_NG_3
    IN_YAML_TEXT:
      west_bound_longitude:
           action: attribute_not_null
           attr2set: defaut_west_bound_longitude

      east_bound_longitude:
           action: attribute_not_null
           attr2set: defaut_east_bound_longitude

      north_bound_latitude:
           action: attribute_not_null
           attr2set: defaut_north_bound_latitude

      south_bound_latitude:
           action: attribute_not_null
           attr2set: defaut_south_bound_latitude
    -> AttributeCopier
UNKNOWN_SPATIAL_EXTENT (writer XLSXW_1)
    attributes: id string(200), north_bound_latitude_to_validate string(200), south_bound_latitude_to_validate string(200), east_bound_longitude_to_validate string(200), west_bound_longitude_to_validate string(200)

Bookmark: Attribute value mapper
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
AttributeCopier
    ATTR_TABLE = COPY resource_update_cycle > progress_code
    MISSING_INPUT_ATTRS = PRESERVE
    -> METADATA_VALUE_MAPPER_NG_14 [DATA_INPUT]
Note: resources{}.language
METADATA_VALUE_MAPPER_NG_14
    ATT_TO_MAP = resources{}.language
    CODE_REFRESH = NO
    ENGLISH_REFRESH = YES
    ERROR_NOT_MAPPED = YES
    FEATURE_TYPE = TransferLang_AB
    FRENCH_REFRESH = NO
    IN_CSV_LOOKUP_TABLES_DIR = $(IN_CSV_LOOKUP_TABLES_DIR)
    P-T_ABBR = $(P-T_ABBR)
    -> METADATA_VALUE_MAPPER_NG_2 [DATA_INPUT]
Note: resource_update_cycle
METADATA_VALUE_MAPPER_NG_2
    ATT_TO_MAP = resource_update_cycle
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_FORMAT_MAPPER_NG [DATA_INPUT]
Note: resources{}.format
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_Geo (writer XLSXW_1)
    -> METADATA_VALUE_MAPPER_NG_15 [DATA_INPUT]
UNKNOWN_MIME_TYPE_Geo (writer XLSXW_1)
    attributes: _unknown_mime_type string(8), _url_validation string(8), id string(8)
Note: Role
METADATA_VALUE_MAPPER_NG_15
    ATT_TO_MAP = contact_role
    CODE_REFRESH = YES
    ENGLISH_REFRESH = YES
    ERROR_NOT_MAPPED = YES
    FEATURE_TYPE = Role
    FRENCH_REFRESH = YES
    IN_CSV_LOOKUP_TABLES_DIR = $(IN_CSV_LOOKUP_TABLES_DIR)
    P-T_ABBR = $(P-T_ABBR)
    -> METADATA_VALUE_MAPPER_NG_3 [DATA_INPUT]
Note: progress_code
METADATA_VALUE_MAPPER_NG_3
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_4 [DATA_INPUT]
Note: spatial_representation_type
METADATA_VALUE_MAPPER_NG_4
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_VALUE_MAPPER_NG_5 [DATA_INPUT]
Note: spatialref{}.projection_name
METADATA_VALUE_MAPPER_NG_5
    ATT_TO_MAP = spatialref{}.projection_name
    CODE_REFRESH = NO
    ENGLISH_REFRESH = YES
    ERROR_NOT_MAPPED = NO
    FEATURE_TYPE = SpatialRef
    FRENCH_REFRESH = NO
    IN_CSV_LOOKUP_TABLES_DIR = $(IN_CSV_LOOKUP_TABLES_DIR)
    P-T_ABBR = $(P-T_ABBR)
    -> METADATA_VALUE_MAPPER_NG_6 [DATA_INPUT]
Note: spatialref{}.projection_system
METADATA_VALUE_MAPPER_NG_6
    ATT_TO_MAP = spatialref{}.projection_system
    CODE_REFRESH = NO
    ENGLISH_REFRESH = YES
    ERROR_NOT_MAPPED = NO
    FEATURE_TYPE = Codespace
    FRENCH_REFRESH = NO
    IN_CSV_LOOKUP_TABLES_DIR = $(IN_CSV_LOOKUP_TABLES_DIR)
    P-T_ABBR = $(P-T_ABBR)
    -> METADATA_VALUE_MAPPER_NG_7 [DATA_INPUT]
Note: ISO Topic
METADATA_VALUE_MAPPER_NG_7
    ATT_TO_MAP = iso_topic{}.topic_value
    CODE_REFRESH = NO
    ENGLISH_REFRESH = YES
    ERROR_NOT_MAPPED = YES
    FEATURE_TYPE = Topic
    FRENCH_REFRESH = NO
    IN_CSV_LOOKUP_TABLES_DIR = $(IN_CSV_LOOKUP_TABLES_DIR)
    P-T_ABBR = $(P-T_ABBR)
    -> METADATA_VALUE_MAPPER_ERROR_MANAGER

Bookmark: Managin error
Note: Creates list of errors found and not corrected in mapping
METADATA_VALUE_MAPPER_ERROR_MANAGER
    ERROR_OUTPUT -> METADATA_MAPPING_ERRORS (writer XLSXW_1)
    DATA_OUTPUT -> MORE_INFO_MANAGER
METADATA_MAPPING_ERRORS (writer XLSXW_1)
    attributes: id auto(20), error auto(20)

Bookmark: Data prepartion for medadata section
Note: Tests the more_info{}.link list for valid attribute values and filters them out where missing
MORE_INFO_MANAGER
    -> AttributeExposer_5
AttributeExposer_5
    ATTR_TABLE = resources{},
    -> ListCopier
ListCopier
    DEST_LIST = distributionList
    SRC_LIST = resources{}
    -> GMD_SECTION_DATA_EXTRACTION
Note: Creates lists and removes duplicates for GMD_Section
GMD_SECTION_DATA_EXTRACTION
    -> REMOVE_BROKEN_URL_WMS_ESRI_REST

Bookmark: Drop Broken Web Services
REMOVE_BROKEN_URL_WMS_ESRI_REST
    URL_VALIDATION = Yes
    -> WMS_REST_LANGUAGE_FORMATTER
    FAULTY_URL_OUTPUT -> MAP_SERVICE_URL_ERRORMAP (writer XLSXW_1)
MAP_SERVICE_URL_ERRORMAP (writer XLSXW_1)
    attributes: id string(200), url string(200), format string(200), _url_failure_message string(20)

Bookmark: HNAP RULES
WMS_REST_LANGUAGE_FORMATTER
    -> AttributeExposer_15
DUPLICATE_SERVICE_REMOVER
    -> GMD_SECTION_DATA_EXTRACTION_2
GMD_SECTION_DATA_EXTRACTION_2
    -> AttributeCreator

Bookmark: New Bookmark
AttributeExposer_15
    ATTR_TABLE = resources{}.format,,resources{}.url,,id,
    -> ListSearcher
Note: If there is an ESRI REST resource
ListSearcher
    ATTR_VALUE = REST
    CASE = CASE_SENSITIVE
    INDEX_ATTR = _list_index
    LIST_ATTR = resources{}.format
    MATCHTYPE = REGULAR_EXPRESSION_ENCODED
    FOUND -> PythonCaller_7
    NOT_FOUND -> DUPLICATE_SERVICE_REMOVER
Note: If format = WMS and there is an ESRI REST format, change resources{}.protocol to 'HTTPS' and xlink_role to NULL to avoid showing ESRI REST and WMS in the viewer; and keep only one WMS feature. / The resources_validator CT is used to reset indexes in the resources list.
PythonCaller_7
    PYTHONSOURCE:
      import fme
      import fmeobjects
      from Python.FME_utils import FME_utils


      def FeatureProcessor(feature):
          dict_1 = {}
          dict_2 = {}

          max_index=FME_utils.max_index_attribute_list(feature,'resources{}')
          for j in range(max_index+1):
              format = feature.getAttribute('resources{%i}.format'%(j))
              url = feature.getAttribute('resources{%i}.url'%(j))

              if format == 'WMS':
                dict_1[url] = j
                feature.setAttribute('resources{%i}.protocol'%(j),'HTTPS')
                feature.setAttributeNullWithType('resources{%i}.xlink_role'%(j),fmeobjects.FME_ATTR_ENCODED_STRING)

              elif (format == 'ESRI REST') and (url.endswith('/WMS')):
                dict_2[url] = j
                feature.setAttribute('resources{%i}.protocol'%(j),'HTTPS')
                feature.setAttributeNullWithType('resources{%i}.xlink_role'%(j),fmeobjects.FME_ATTR_ENCODED_STRING)

          max_index=FME_utils.max_index_attribute_list(feature,'resources{}')
          for j in range(max_index+1):
              format = feature.getAttribute('resources{%i}.format'%(j))
              url = feature.getAttribute('resources{%i}.url'%(j))

              if format == 'WMS':
                 if j == dict_1[url]:
                    feature.removeAttrsWithPrefix('resources{%i}'%(j))

              elif (format == 'ESRI REST') and (url.endswith('/WMS')):
                 if j == dict_2[url]:
                    feature.removeAttrsWithPrefix('resources{%i}'%(j))
    PYTHONSYMBOL = FeatureProcessor
    -> RESOURCES_VALIDATOR_3
RESOURCES_VALIDATOR_3
    -> DUPLICATE_SERVICE_REMOVER

Bookmark: Configuring publishing info
AttributeCreator
    ATTR_TABLE = SET_TO csw_url (varchar(200)) = $(FORCED_PYCSW_URL)
    -> ATTRIBUTE_MANAGER_NG_4
AttributeExposer_3
    ATTR_TABLE = search_criteria_pycsw,,csw_url,,record_last_modified,
    -> METADATA_DELTA_FINDER_GEN
METADATA_DELTA_FINDER_GEN
    ATTR_DATE_MODIFIED = record_last_modified
    CSW_FILTER = @Value(search_criteria_pycsw)
    LOCAL_SOURCE = $(LOCAL_SOURCE_METADATA_DELTA_FINDER)
    METADATA_OVERWRITE = $(METADATA_OVERWRITE)
    METADATA_TYPE = XML-HNAP
    SOURCE_DIRECTORY = $(OUT_XML_LOCAL_DIR)
    SOURCE_URL = @Value(csw_url)
    VALIDATE_INSERT_PCT = $(VALIDATE_INSERT_PCT_XML)
    YAML_FILE = $(IN_CSV_LOOKUP_TABLES_DIR)\$(P-T_ABBR)\metadata_delta_finder_$(P-T_ABBR)_geo.yaml
    Statistics -> StatisticsCalculator_Summary
    Update -> Junction_2
    Insert -> Junction_2
    Delete -> AttributeExposer_17
Junction_2
    -> AWS_TRANSLATE
AttributeExposer_17
    ATTR_TABLE = id,,title,
    -> DELETED_RECORDS (writer XLSXW_1)

Bookmark: Listes Metadata_delta_finder
ATTRIBUTE_MANAGER_NG_4
    IN_YAML_TEXT:
      contacts{0}.role_code:
         action: attribute_not_null
         attr2set: contact_role_code
      contacts{0}.role:
         action: attribute_not_null
         attr2set: contact_role
      contacts{0}.role_fr:
         action: attribute_not_null
         attr2set: contact_role_fr
      contacts{0}.p-t_entity:
         action: attribute_not_null
         attr2set: p-t_entity
      contacts{0}.p-t_entity_fr:
         action: attribute_not_null
         attr2set: p-t_entity_fr
      contacts{0}.sector:
         action: attribute_not_null
         attr2set: sector
      projectionList{0}.projection_name:
         action: attribute_not_null
         attr2set: spatialref_projection_name
      projectionList{0}.reference_system:
         action: attribute_not_null
         attr2set: spatialref_projection_system
      projectionList{0}.reference_system_version:
         action: attribute_not_null
         attr2set: spatialref_projection_system_version
      distributionList{0}.format_version:
         action: attribute_not_null
         attr2set: distribution_format_version
    -> ATTRIBUTE_MANAGER_NG_5
ATTRIBUTE_MANAGER_NG_5
    IN_YAML_TEXT:
      contacts{}.role_code:
         action: attribute_not_null
         attr2set: contact_role_code
      contacts{}.role:
         action: attribute_not_null
         attr2set: contact_role
      contacts{}.role_fr:
         action: attribute_not_null
         attr2set: contact_role_fr
      contacts{}.p-t_entity:
         action: attribute_not_null
         attr2set: p-t_entity
      contacts{}.p-t_entity_fr:
         action: attribute_not_null
         attr2set: p-t_entity_fr
      contacts{}.sector:
         action: attribute_not_null
         attr2set: sector
      projectionList{}.projection_name:
         action: attribute_not_null
         attr2set: spatialref_projection_name
      projectionList{}.reference_system:
         action: attribute_not_null
         attr2set: spatialref_projection_system
      projectionList{}.reference_system_version:
         action: attribute_not_null
         attr2set: spatialref_projection_system_version
      distributionList{}.format_version:
         action: attribute_not_null
         attr2set: distribution_format_version
    -> AttributeExposer_3

Bookmark: New Bookmark
StatisticsCalculator_Summary: Logger
    LOG_FEATURE = LOG_RECORD
    MAXCOORDS = 20
    MAXFEATS = 20
    MESSAGE:
      ************************
      **** Unchanged Report ****
      ************************

      @Value(_real_count) features were unchanged

      ************************
      ************************
      ************************
    SEVERITY = INFO

Bookmark: Language Translation
AWS_TRANSLATE
    ACTIVATE_TRANSLATION = $(ACTIVATE_TRANSLATION)
    ATTR_2_TRANSLATE = notes,title
    ATTR_LIST_2_TRANSLATE = tags{}.display_name,resources{}.name
    MODE = English-->French
    -> XML_PUBLISHER_NG_2
    TRANSLATION_PROBLEM -> AttributeExposer_16
AttributeExposer_16
    ATTR_TABLE = id,,title,
    -> TRANSLATION_PROBLEMS_GEO (writer XLSXW_1)
TRANSLATION_PROBLEMS_GEO (writer XLSXW_1)
    attributes: id auto(20), title auto(20)
DELETED_RECORDS (writer XLSXW_1)
    attributes: id string(200), title string(200)

Bookmark: XML CREATION AND WRITING
Note: Excel config file to map AB attributes to those required by XML templates
XML_PUBLISHER_NG_2
    FEATURE_TYPE = Config_AB
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_2)
    INSERT_PASSED -> text_line (writer TEXTLINE_3)
    UPDATE_PASSED -> text_line (writer TEXTLINE_3)
    INSERT_FAILED -> text_line (writer TEXTLINE_1)
    InvalidMetadata -> INVALID_METADATA_PUBLISHER (writer XLSXW_1)
    UPDATE_FAILED -> text_line (writer TEXTLINE_1)
Note: Writes XML to a local folder without publishing to PyCSW, and without the PyCSW transaction headers and footers
text_line (writer TEXTLINE_2)
    attributes: text_line_data buffer
Note: Writes XML published to the PyCSW to a local folder
text_line (writer TEXTLINE_3)
    attributes: text_line_data buffer
Note: Writes XML that failed to publish to the PyCSW to a local folder
text_line (writer TEXTLINE_1)
    attributes: text_line_data buffer
Note: Extracts and maps attributes to values required by the XML root template or sub-templates, compliles the templates to a single XML file, and publishes the XML to the PyCSW, or to a local folder. / NOTE: The publication method is defaulted to 'Auto', which will read the method attribute set in the CREATE transformer. Can override to 'Local', 'Insert' or 'Update' by selecting option in pubished parameter 'METHOD_SELECT'.
INVALID_METADATA_PUBLISHER (writer XLSXW_1)
    attributes: id string(200)

Bookmark: Samples or full content
TestFilter_2
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_4
    SAMPLES FEATURES -> Sampler_3
Sampler_3
    MODE = ORIGINAL
    RATE = $(SAMPLE_SIZE)
    SAMPLE_TYPE_MULTIPLIER = -1
    SAMPLE_MODE = No
    SAMPLE_TYPE_LONG = First N Features
    SAMPLED -> Junction_4

Bookmark: Non-geospatial processing
Note: Adjusting update frequency value
METADATA_VALUE_MAPPER_NG_10
    ATT_TO_MAP = resource_update_cycle
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> METADATA_FORMAT_MAPPER_NG_2 [DATA_INPUT]
Note: resources{}.format
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_NoneGeo (writer XLSXW_1)
    -> METADATA_VALUE_MAPPER_NG_11 [DATA_INPUT]
Note: resources{}.language
METADATA_VALUE_MAPPER_NG_11
    ATT_TO_MAP = resources{}.language
    CODE_REFRESH = NO
    ENGLISH_REFRESH = YES
    ERROR_NOT_MAPPED = YES
    FEATURE_TYPE = TransferLang_AB_tbs
    FRENCH_REFRESH = NO
    IN_CSV_LOOKUP_TABLES_DIR = $(IN_CSV_LOOKUP_TABLES_DIR)
    P-T_ABBR = $(P-T_ABBR)
    -> AttributeExposer_12
Note: Creates list of errors found and not corrected in mapping
METADATA_VALUE_MAPPER_ERROR_MANAGER_2
    ERROR_OUTPUT -> METADATA_MAPPING_ERRORS_NON_GEO (writer XLSXW_1)
    DATA_OUTPUT -> AttributeExposer_20
Note: Translates specific items from English to French
AWS_TRANSLATE_2
    ACTIVATE_TRANSLATION = $(ACTIVATE_TRANSLATION)
    ATTR_2_TRANSLATE = notes,title
    ATTR_LIST_2_TRANSLATE = tags{}.display_name,resources{}.name
    MODE = English-->French
    -> JSON_PUBLISHER_NG
    TRANSLATION_PROBLEM -> AttributeExposer_14
AttributeExposer_14
    ATTR_TABLE = id,,title,
    -> TRANSLATION_PROBLEMS_NONE_GEO (writer XLSXW_1)
TRANSLATION_PROBLEMS_NONE_GEO (writer XLSXW_1)
    attributes: id auto(20), title auto(20)
METADATA_MAPPING_ERRORS_NON_GEO (writer XLSXW_1)
    attributes: error string(200), id string(200), _element_index number(20)
UNKNOWN_MIME_TYPE_NoneGeo (writer XLSXW_1)
    attributes: _unknown_mime_type string(8), _url_validation string(8), id string(8)

Bookmark: Add 'Government of Alberta' before sector
AttributeExposer_12
    ATTR_TABLE = sector,
    -> StringConcatenator_2
StringConcatenator_2
    ACTION = Create New Attribute
    PARM_LINE = Government of Alberta; @Value(sector)
    VAL_ATTR = sector
    -> AttributeExposer

Bookmark: TOPICS value mapper from iso_topic{}.topic_value list attributes
AttributeExposer
    ATTR_TABLE = iso_topic{}.topic_value,
    -> ListCopier_2
ListCopier_2
    DEST_LIST = topics
    SRC_LIST = iso_topic{}
    -> METADATA_VALUE_MAPPER_NG_12 [DATA_INPUT]
METADATA_VALUE_MAPPER_NG_12
    ATT_TO_MAP = topics{}.topic_value
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUP_TABLES_DIR)
    P-T_ABBR = $(P-T_ABBR)
    -> AttributeExposer_7
AttributeExposer_7
    ATTR_TABLE = topics{}.topic_value,
    -> ListDuplicateRemover
ListDuplicateRemover
    SRC_LIST = topics{}.topic_value
    -> AttributeExposer_10

Bookmark: SUBJECTS value mapper from iso_topic{}.topic_value list attributes
AttributeExposer_10
    ATTR_TABLE = iso_topic{}.topic_value,
    -> ListCopier_3
ListCopier_3
    DEST_LIST = subjects
    SRC_LIST = iso_topic{}
    -> METADATA_VALUE_MAPPER_NG_13 [DATA_INPUT]
METADATA_VALUE_MAPPER_NG_13
    ATT_TO_MAP = subjects{}.topic_value
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUP_TABLES_DIR)
    P-T_ABBR = $(P-T_ABBR)
    -> AttributeExposer_13
AttributeExposer_13
    ATTR_TABLE = subjects{}.topic_value,
    -> ListDuplicateRemover_2
ListDuplicateRemover_2
    SRC_LIST = subjects{}.topic_value
    -> METADATA_VALUE_MAPPER_ERROR_MANAGER_2

Bookmark: Metadata delta finder
AttributeExposer_20
    ATTR_TABLE = search_criteria_pycsw,,csw_url,,record_last_modified,,id,
    -> METADATA_DELTA_FINDER_GEN_2
METADATA_DELTA_FINDER_GEN_2
    ATTR_DATE_MODIFIED = record_last_modified
    LOCAL_SOURCE = Yes
    METADATA_OVERWRITE = $(METADATA_OVERWRITE)
    METADATA_TYPE = JSON-CKANExtCa
    SOURCE_DIRECTORY = $(OUT_JSON_LOCAL_DIR)
    VALIDATE_INSERT_PCT = $(VALIDATE_INSERT_PCT_JSON)
    YAML_FILE = $(IN_CSV_LOOKUP_TABLES_DIR)\$(P-T_ABBR)\metadata_delta_finder_$(P-T_ABBR)_non_geo.yaml
    Statistics -> StatisticsCalculator_Summary_3
    Update -> Junction_6
    Insert -> Junction_6
    Delete -> AttributeExposer_19
Note: Log statistics
StatisticsCalculator_Summary_3: Logger
    LOG_FEATURE = LOG_RECORD
    MAXCOORDS = 20
    MAXFEATS = 20
    MESSAGE:
      ************************
      **** NoneGeo Features: Unchanged Report ****
      ************************

      @Value(_real_count) features were unchanged

      ************************
      ************************
      ************************
    SEVERITY = INFO
Junction_6
    -> AWS_TRANSLATE_2
AttributeExposer_19
    ATTR_TABLE = id,,title,
    -> DELETED_RECORDS_NONE_GEO (writer XLSXW_1)
Note: Log deleted features
DELETED_RECORDS_NONE_GEO (writer XLSXW_1)
    attributes: id auto(20), title auto(20)

Bookmark: JSON creation and writing
JSON_PUBLISHER_NG
    FEATURE_TYPE = JSON_CONFIG_AB
    IN_CSV_LOOKUP_TABLES_DIR = $(IN_CSV_LOOKUP_TABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.display_name
    Keywords_FR = tags{}.display_name_fr
    P-T_ABBR = $(P-T_ABBR)
    Subject_LIST = subjects{}.topic_value
    Topic_LIST = topics{}.topic_value
    OUTPUT_LOCAL -> AttributeExposer_8
AttributeExposer_8
    ATTR_TABLE = json_file,,id,
    -> AttributeCreator_6
AttributeCreator_6
    ATTR_TABLE = SET_TO text_line_data (varchar(200)) = @Value(json_file)
    -> text_line (writer TEXTLINE_4)
text_line (writer TEXTLINE_4)
    attributes: text_line_data buffer
