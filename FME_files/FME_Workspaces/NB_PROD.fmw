FME workspace NB_PROD.fmw
Title: NB_PROD
Description: Description 
This workbench read and trasform all the metadata for the province of New Brunswick (NB)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
SAMPLE_SIZE: Number of features to process. Zero (0) means process all the features. A number n greater than 0 means sample or process only the first n features.
URL_VALIDATION : Indicates to validate or not created URL. (Should be Yes for prod)
VALIDATE_INSERT_PCT :Indicates to valide insert percentage. 75 % or less insert/update record  (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = NO
- IN_OUT_WORKING_DIR = $(FME_SHAREDRESOURCE_DATA)\PT_Harvester
- SAMPLE_SIZE = 0
- URL_VALIDATION = Yes
- VALIDATE_INSERT_PCT_JSON = Yes
- VALIDATE_INSERT_PCT_XML = Yes
- IN_CSV_LOOKUP_TABLES_DIR = $(IN_OUT_WORKING_DIR)\LOOKUP_TABLES
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\NB.log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_LOCAL_DIR = $(IN_OUT_WORKING_DIR)\$(P-T_ABBR)\XML_LOCAL
- OUT_XML_FAILED_DIR = $(IN_OUT_WORKING_DIR)\$(P-T_ABBR)\XML_FAILED
- OUT_XML_PASSED_DIR = $(IN_OUT_WORKING_DIR)\$(P-T_ABBR)\XML_PASSED
- FME_SHAREDRESOURCE_DATA = C:\Data   # FME Flow Data Directory

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_LOCAL_DIR)

SPATIAL_TYPE_MAPPER_FAILED (writer XLSXW_1)
    attributes: id string(200), title string(200), notes string(200)
TestFilter
    DEFAULT_VALUE = <UNFILTERED>
    PASSED_TEST_GROUP_OUTPUT = FIRST
    TEST_LIST = "BOOL_OP,OR,COMPOSITE_TEST,""""""1"""""",TEST_CLAUSE,TEST @LowerCase($(ACTIVATE_GEO)) = yes",GEO_ACTIVATE
    GEO_ACTIVATE -> TestFilter_3
Junction
    -> Socrata_BoundingBoxExtractor [feature_input]
Note: Extraction des coordonnées du BBOX
Socrata_BoundingBoxExtractor: SOCRATA_BOUNDING_BOX_EXTRACTOR
    DOMAIN = https://gnb.socrata.com
    SocrataAppToken = FL3Cxsebg0Vf6JQ0CnbMujHkQ
    feature_output -> METADATA_VALUE_MAPPER_NG [DATA_INPUT]
DELETEDRECORDS_GEO (writer XLSXW_1)
    attributes: id string(200), timestamp string(200)
Junction_4
    -> AWS_TRANSLATE_6
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
INVALID_METADATA (writer XLSXW_1)
    attributes: id auto(20)
TRANSLATION_PROBLEMS_GEO (writer XLSXW_1)
    attributes: id string(20), title string(20)
TestFilter_2
    DEFAULT_VALUE = <UNFILTERED>
    PASSED_TEST_GROUP_OUTPUT = FIRST
    TEST_LIST = "BOOL_OP,OR,COMPOSITE_TEST,""""""1"""""",TEST_CLAUSE,TEST @LowerCase($(ACTIVATE_NON_GEO)) = yes",NON-GEO_ACTIVATE
    NON-GEO_ACTIVATE -> TestFilter_4
Junction_2
    -> ATTRIBUTE_MANAGER_NG_6
AttributeExposer_2
    ATTR_TABLE = search_criteria_pycsw,,csw_url,,record_last_modified,,id,,tbs_topic,,tbs_subject,
    -> AttributeCreator_2
AttributeCreator_2
    ATTR_TABLE:
      SET_TO TBS_Topic{0}.value (varchar(200)) = @Value(tbs_topic)
      SET_TO TBS_Subject{0}.value (varchar(200)) = @Value(tbs_subject)
    -> METADATA_DELTA_FINDER_GEN_2
DELETED_RECORDS_NONE_GEO (writer XLSXW_1)
    attributes: id string(200), title string(200)
Junction_3
    -> AWS_TRANSLATE_2
TRANSLATION_PROBLEMS_NONE_GEO (writer XLSXW_1)
    attributes: id string(20), title string(20)
UNKNOWN_MIME_TYPE (writer XLSXW_1)
    attributes: id string(200), _url_validation string(200), _unknown_mime_type string(200)

Bookmark: lecture des données du portail socrata, filtrage de licence et fusion des métadonnées de vue externe
Creator_3
    GEOMTYPE = Geometry Object
    NUM = 1
    CREATED -> Tester_6
Tester_6
    BOOL_OP = OR
    TEST_CLAUSE = TEST $(CATALOGUE_READER_SELECT) = Yes
    TEST_MODE = TEST
    PASSED -> SOCRATA_READER_NG
    FAILED -> FeatureReader_2 [INITIATOR]
SOCRATA_READER_NG
    DOMAIN = "https://gnb.socrata.com "
    -> AttributeExposer_3
FeatureReader_2
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> AttributeExposer_3
AttributeExposer_3
    ATTR_TABLE = licenseId,,id,,title,
    -> NullAttributeMapper
Note: If there is no license: modify value to unknown (fgp_publish=non)
NullAttributeMapper
    ATTRCHOICE_ACTION = SELECTED
    ATTRLIST = licenseId
    NEW_VALUE = unknown
    NULL_TREATMENT_LU = SETVALUE
    SOURCE_ATTR_VAL_LU = MISSINGATTR
    ATTRCHOICE = Selected Attributes
    NULL_TREATMENT = New Value
    SOURCE_ATTR_VAL = "Missing (Selected Attributes Only)"
    -> LICENSE_FILTER_NG
LICENSE_FILTER_NG
    FEATURE_TYPE = License_NB
    IN_CSV_LOOKUP_TABLES_DIR = $(IN_CSV_LOOKUP_TABLES_DIR)
    LICENSE_ATT = @Value(licenseId)
    P-T_ABBR = $(P-T_ABBR)
    LICENSE_FILTER_PASSED -> SOCRATA_METADATA_MERGER
    UNKNOWN_LICENSE -> UNKNOWN_LICENCE (writer XLSXW_1)
SOCRATA_METADATA_MERGER
    DOMAIN = https://gnb.socrata.com
    -> DEFAULT_ATTRIBUTE_MAPPER_NG
    UnmergedAdvancedView -> UNMERGED_ADVANCED_VIEW (writer XLSXW_1)
UNMERGED_ADVANCED_VIEW (writer XLSXW_1)
    attributes: _seriesID string(200), url string(200), format string(200)
UNKNOWN_LICENCE (writer XLSXW_1)
    attributes: id string(200), license_id string(200), title string(200)

Bookmark: Transformation vers modèle de travail et ajout des valeurs par défeauts
Note: Set default attribute values
DEFAULT_ATTRIBUTE_MAPPER_NG
    FEATURE_TYPE = Default_NB
    IN_CSV_LOOKUP_TABLES_DIR = $(IN_CSV_LOOKUP_TABLES_DIR)
    P-T_ABBR = $(P-T_ABBR)
    -> AttributeExposer_13
Note: Gestion des attributs
ATTRIBUTE_MANAGER_NG
    IN_YAML_TEXT:
      # Create a new resource.id attribute
      resource.id:
          action: attribute_overwrite
          attr2set: id
      #
      # Create a new resource.type attribute
      resource.type:
          action: attribute_overwrite
          attr2set: assetType
      #
      # Default value for tags{} if null
      tags{0}:
          action: attribute_not_null
          attr2set: default_domain_tag
      #
      # Default value for category if null
      category:
          action: attribute_not_null
          attr2set: default_category
      #
      # Create a new sector attribute
      sector:
          action: attribute_overwrite
          attr2set: metadata.custom_fields.Department / Ministère.Department / Ministère
      #
      # Création de l'attribut pour record_last_modified
      record_last_modified:
          action: attribute_overwrite
          attr2set: viewLastModified
      #
      # Création de l'attribut pour record_publish_date
      record_publish_date:
          action: attribute_overwrite
          attr2set: publicationDate
      #
      # Création de l'attribut pour record_create_date
      record_create_date:
          action: attribute_overwrite
          attr2set: createdAt
    -> ATTRIBUTE_MANAGER_NG_2
Note: Utiliser l'attribut attribution s'il n'y pas sector défini
ATTRIBUTE_MANAGER_NG_2
    IN_YAML_TEXT:
      # Set attribution if sector_temps is null
      sector:
          action: attribute_not_null
          attr2set: attribution
    -> ATTRIBUTE_MANAGER_NG_3
Note: Utilisation de la valeur par défaut si pas de secteur
ATTRIBUTE_MANAGER_NG_3
    IN_YAML_TEXT:
      # Default value for sector if null
      sector:
          action: attribute_not_null
          attr2set: default_sector
    -> AttributeExposer_19
AttributeExposer_19
    ATTR_TABLE = sector,
    -> AttributeSplitter
Note: Séparation en/fr de l'attribut sector_temp avec le "/" comme séparateur.
AttributeSplitter
    ATTR_NAME = sector
    DELIMITER = /
    DROP_EMPTY_PARTS = NO
    LIST_NAME = _list
    TRIM_TYPE = BOTH
    -> ATTRIBUTE_MANAGER_NG_4
Note: Définition du sector et sector_fr avec les 2 portilons de la liste
ATTRIBUTE_MANAGER_NG_4
    IN_YAML_TEXT:
      sector:
          action: attribute_overwrite
          attr2set: _list{0}

      sector_fr:
          action: attribute_overwrite
          attr2set: _list{1}
    -> ATTRIBUTE_MANAGER_NG_5
Note: Si pas de contenu français pour le secteur, on met l'anglais dans le fraçais
ATTRIBUTE_MANAGER_NG_5
    IN_YAML_TEXT:
      sector_fr:
          action: attribute_not_null
          attr2set: _list{0}
    -> AttributeExposer_20
AttributeExposer_20
    ATTR_TABLE = _list{},,resource.id,
    -> AttributeRemover_9
AttributeRemover_9
    LIST_ATTRS = _list{}
    -> UNIQUE_ID_CREATOR
UNIQUE_ID_CREATOR
    UNIQUE_ATT = @Value(resource.id)
    -> SECTOR_MAPPER_NG

Bookmark: Date conversion
AttributeExposer_13
    ATTR_TABLE = publicationDate,,createdAt,,viewLastModified,,id,
    -> DateTimeConverter
Note: Formats all date fields to ISO yyyy-mm-dd
DateTimeConverter
    DATETIME_ATTR = viewLastModified createdAt publicationDate
    IN_FORMAT = %s$
    OUT_FORMAT = %Y-%m-%d
    PASSTHROUGH = NO
    REPAIR_INPUT = YES
    TEST_INPUT = 1611946240
    -> ATTRIBUTE_MANAGER_NG
    <REJECTED> -> ERROR_DATETIME (writer XLSXW_1)
ERROR_DATETIME (writer XLSXW_1)
    attributes: id string(20), publicationDate string(200), fme_rejection_code string(20)

Bookmark: Sector filtering (Drop federal dataset)
SECTOR_MAPPER_NG
    FEATURE_TYPE = Sector_NB
    IN_CSV_LOOKUP_TABLES_DIR = $(IN_CSV_LOOKUP_TABLES_DIR)
    P-T_ABBR = $(P-T_ABBR)
    PUBLISHED_OUTPUT -> AttributeExposer_18
    UNMAPPED_OUTPUT -> SECTOR_NB_missing_sector (writer XLSXW_1)
AttributeExposer_18
    ATTR_TABLE = resource.id,,name,,description,
    -> Tester_3
Note: Supprimer les datasets : / - Map viewer du NB (ksan-r62m) / - Federal Electoral Districts / Circonscriptions électorales fédérales (dgwg-z6d7)
Tester_3
    BOOL_OP = COMPOSITE
    COMPOSITE_TEST = 1 AND 2
    TEST_CLAUSE:
      TEST @Value(resource.id) != ksan-r62m
      TEST @Value(resource.id) != dgwg-z6d7
    TEST_MODE = TEST
    PASSED -> NB_FrenchEnglishAttributeSeparator_NG [Feature_Input]
SECTOR_NB_missing_sector (writer XLSXW_1)
    attributes: id string(200), sector string(200)

Bookmark: Gestion des champs bilingues pour distinguer le contenu FR versus EN
Note: Description to Notes
NB_FrenchEnglishAttributeSeparator_NG
    ATTRIBUTE_TO_SPLIT = description
    FEATURE_TYPE = NB_SlashCountSeparatorForDesc
    IN_CSV_LOOKUP_TABLES_DIR = $(IN_CSV_LOOKUP_TABLES_DIR)
    P-T_ABBR = $(P-T_ABBR)
    Feature_Output -> AttributeRenamer
    MULTIPLE_UNCAUGHT_SLASH_IN_ATT -> AttributeExposer_25
AttributeRenamer
    ATTR_TABLE:
      RENAME_SET_DEFAULT splited_attr_en > notes
      RENAME_SET_DEFAULT splited_attr_fr > notes_fr
    KEEP_RENAMED_ONLY = no
    MISSING_INPUT_ATTRS = PRESERVE
    -> NB_FrenchEnglishAttributeSeparator_NG_2 [Feature_Input]
Note: Name to Title
NB_FrenchEnglishAttributeSeparator_NG_2
    ATTRIBUTE_TO_SPLIT = name
    FEATURE_TYPE = NB_SlashCountSeparatorForName
    IN_CSV_LOOKUP_TABLES_DIR = $(IN_CSV_LOOKUP_TABLES_DIR)
    P-T_ABBR = $(P-T_ABBR)
    Feature_Output -> AttributeRenamer_2
    MULTIPLE_UNCAUGHT_SLASH_IN_ATT -> AttributeExposer_27
AttributeRenamer_2
    ATTR_TABLE:
      RENAME_SET_DEFAULT splited_attr_en > title
      RENAME_SET_DEFAULT splited_attr_fr > title_fr
    KEEP_RENAMED_ONLY = no
    MISSING_INPUT_ATTRS = PRESERVE
    -> ATTRIBUTE_MANAGER_NG_9
Note: Transférer le titre anglais dans FR si pas de baleur. Titre bilingue
ATTRIBUTE_MANAGER_NG_9
    IN_YAML_TEXT:
      title_fr:
         action: attribute_not_null
         attr2set: title
    -> AttributeExposer_12
AttributeExposer
    ATTR_TABLE = resource.id,
    -> GEOPORTAL_WEBLINK_ADDER_NG
AttributeExposer_27
    ATTR_TABLE = Socrata_id,,slash_count,,resource_id,,id,
    -> NB_MULTIPLE_SLASH_IN_NAME (writer XLSXW_1)
NB_MULTIPLE_SLASH_IN_NAME (writer XLSXW_1)
    attributes: resource.id string(200), name string(200), slash_count number(20)
AttributeExposer_25
    ATTR_TABLE = Socrata_id,,link,,description,,datetime,,id,
    -> NB_MULTIPLE_SLASH_IN_DESCRIPTION (writer XLSXW_1)
NB_MULTIPLE_SLASH_IN_DESCRIPTION (writer XLSXW_1)
    attributes: resource.id string(200), name string(200), description string(200), slash_count number(20)

Bookmark: transforming tags{} as tags{}.display_name
AttributeExposer_12
    ATTR_TABLE = tags{},
    -> PythonCaller_6
PythonCaller_6
    PYTHONSOURCE:
      import fme
      import fmeobjects
      from Python.FME_utils import FME_utils

      # Template Function interface:
      # When using this function, make sure its name is set as the value of
      # the 'Class or Function to Process Features' transformer parameter
      def FeatureProcessor(feature):
          i=0

          max_index=FME_utils.max_index_attribute_list(feature,'tags{}')
          for j in range(max_index+1):
              feature.setAttribute('tags{%i}.display_name'%(i),feature.getAttribute('tags{%i}'%(j)))
              i=i+1
    PYTHONSYMBOL = FeatureProcessor
    -> ATTRIBUTE_UNEXPOSER_2
ATTRIBUTE_UNEXPOSER_2
    -> AttributeExposer

Bookmark: Création de la liste des ressources pour les jeux de données
Note: NOTE: SI ON EST EN MODE URL_VALIDATION=NO --> ON A MOINS D'ENTITÉS CAR LES ADVANCED_VIEW ET INSIDE_DB_EXTRACTOR ON BESOIN DE FAIRE DES APPELS HTTP POUR AVOIR LES DONNÉES.
Note: Création de la liste resources
GEOPORTAL_WEBLINK_ADDER_NG
    FEATURE_TYPE = GeoportalWeblink_NB
    IN_CSV_LOOKUP_TABLES_DIR = $(IN_CSV_LOOKUP_TABLES_DIR)
    P-T_ABBR = $(P-T_ABBR)
    URL_VALIDATION = $(URL_VALIDATION)
    WEBLINK_WILDCARD = @Value(resource.id)
    -> SOCRATA_ADDITIONAL_ACCESS_POINTS_RESOURCES_EXTRACTOR
Note: Extraction des ressources dans additional access points / Crée la liste / additional_access_points_resources
SOCRATA_ADDITIONAL_ACCESS_POINTS_RESOURCES_EXTRACTOR
    -> SOCRATA_ATTACHEMENTS_EXTRACTOR
Note: Extraction des resources dans les attachements / Crée la liste attachement_resources
SOCRATA_ATTACHEMENTS_EXTRACTOR
    SBN_URL_ROOT = https://gnb.socrata.com
    URL_VALIDATION = $(URL_VALIDATION)
    -> SOCRATA_ADVANCED_VIEW_EXTRACTOR
Note: Extraction des ressources dans les vues avanacées / Crée la liste advancedview_resources
SOCRATA_ADVANCED_VIEW_EXTRACTOR
    -> SOCRATA_INSIDE_DB_EXTRACTOR_NG
SOCRATA_INSIDE_DB_EXTRACTOR_NG
    DOMAIN = https://gnb.socrata.com
    Field_datatype = NB_FieldType_NG
    Field_name = NB_GeoDataFieldName
    IN_CSV_LOOKUP_TABLES_DIR = $(IN_CSV_LOOKUP_TABLES_DIR)
    LinkBuilderNonGeo = NB_LINKBUILDER_NONGEO
    P-T_ABBR = $(P-T_ABBR)
    URL_VALIDATION = $(URL_VALIDATION)
    linkbuilder_geo = NB_LINKBUILDER_GEO
    -> AttributeExposer_5
    Unknown_field_datatype -> UNKNOWN_FILD_DATATYPE (writer XLSXW_1)
URL_HTTPS_MAKER
    P-T_ABBR = $(P-T_ABBR)
    URL_VALIDATION = $(URL_VALIDATION)
    -> EMPTY_FORMAT_MAPPER_NG [DATA_INPUT]
Note: Extraction du format
EMPTY_FORMAT_MAPPER_NG
    CSV_FORMAT = Format
    CSV_MIME_TYPE = Mime_type
    IN_CSV_LOOKUP_TABLES_DIR = $(IN_CSV_LOOKUP_TABLES_DIR)
    P-T_ABBR = $(P-T_ABBR)
    URL_VALIDATION = $(URL_VALIDATION)
    DATA_OUTPUT -> AttributeExposer_7
    UNKNOWN_MIME_TYPE -> UNKNOWN_MIME_TYPE (writer XLSXW_1)
UNKNOWN_FILD_DATATYPE (writer XLSXW_1)
    attributes: fieldName string(200), dataTypeName string(200), _sub_uuid string(20)

Bookmark: Fusion des listes de resources dans une seule liste
AttributeExposer_5
    ATTR_TABLE = resources{}.url,,resources_copy{},,socrata_db_resources{},,advancedview_resources{},,additional_access_points_resources{},,attachement_resources{},
    -> ListCopier
ListCopier
    DEST_LIST = resources_copy
    SRC_LIST = resources{}
    -> AttributeRemover
AttributeRemover
    LIST_ATTRS = resources{}
    -> PythonCaller_3
PythonCaller_3
    NEW_ATTRIBUTES = resources{}.name buffer resources{}.url buffer resources{}.format buffer resources{}.name_fr buffer
    PYTHONSOURCE:
      import fme
      import fmeobjects
      logger = fmeobjects.FMELogFile()
      # Template Function interface:
      # When using this function, make sure its name is set as the value of
      # the 'Class or Function to Process Features' transformer parameter
      def processFeature(feature):
          list_list_name=[r'resources_copy',r'socrata_db_resources',r'advancedview_resources',r'additional_access_points_resources',r'attachement_resources']
          list_attr_name=[r'format',r'url',r'name',r'name_fr',r'spatial_type']

          i=0





          for list_name in list_list_name:

              #Extracting number of resources
              list_url=feature.getAttribute('%s{}.url'%(list_name))
              if list_url:
                  #Looping in resources
                  for j in range(len(list_url)):
                      #Looping in attributes
                      for attr_name in list_attr_name:
                          feature.setAttribute('resources{%i}.%s'%(i,attr_name),feature.getAttribute('%s{%i}.%s'%(list_name,j,attr_name)))

                      #Changing index feature where new features
                      i=i+1
    PYTHONSYMBOL = processFeature
    -> ListDuplicateRemover_2
Note: Removing dupplicates on URL
ListDuplicateRemover_2
    SRC_LIST = resources{}.url
    -> AttributeRemover_7
AttributeRemover_7
    LIST_ATTRS = socrata_db_resources{} resources_copy{} advancedview_resources{} additional_access_points_resources{} attachement_resources{}
    -> ListElementCounter_2

Bookmark: Enlever les jeux de données avec seulement un lien vers la donnée source
ListElementCounter_2
    CNT_ATTR = _element_count
    LIST_NAME = resources{}
    -> Tester
Tester
    BOOL_OP = OR
    TEST_CLAUSE = TEST @Value(_element_count) > 1
    TEST_MODE = TEST
    PASSED -> URL_HTTPS_MAKER [UUIDGenerator_Input]

Bookmark: Création d'une liste avec les catégories pour pouvoir fouiller dedans avec le Geospatial data validator
AttributeExposer_7
    ATTR_TABLE = category,
    -> AttributeCreator_6
AttributeCreator_6
    ATTR_TABLE = SET_TO category{0}.value (varchar(200)) = @LowerCase(@Value(category))
    -> GEO_NONE_GEO_SELECTOR

Bookmark: Filtrage geo / non-geo
GEO_NONE_GEO_SELECTOR
    CSV_FILE_NAME = GeospatialValidation
    CSV_PATH = $(IN_CSV_LOOKUP_TABLES_DIR)
    CSV_PROVINCE = $(P-T_ABBR)
    YAML_DIRECTIVES:
      resources{}.format:
        domain: lookup_table_format
        spatial_type: if_null_overwrite
        not_found: log
        search_type: equals
      #
      category{}.value:
        domain: [lidar, geographic]
        spatial_type: no_overwrite
        not_found: no_log
        search_type: contains
    GEOSPATIAL -> AttributeExposer_8
    NONE_GEOSPATIAL -> AttributeExposer_9
    LOG_ERROR -> AttributeExposer_26
AttributeExposer_8
    ATTR_TABLE = category{},
    -> AttributeRemover_3
Note: Suppression de la liste temporaire
AttributeRemover_3
    LIST_ATTRS = category{}
    -> AttributeExposer_4
AttributeExposer_28
    ATTR_TABLE = id,,title,,notes,
    -> SPATIAL_TYPE_MAPPER_FAILED (writer XLSXW_1)
AttributeExposer_22
    ATTR_TABLE = id,,id_temp,
    -> AttributeManager
AttributeManager
    ATTR_TABLE:
      SET_TO id (varchar(200)) = @Value(id_temp)
      REMOVE id_temp (varchar(200))
    -> AttributeCreator_13
AttributeExposer_26
    ATTR_TABLE = _timestamp,
    -> GEOSPATIAL_FORMAT_NOT_MAPPED (writer XLSXW_1)
GEOSPATIAL_FORMAT_NOT_MAPPED (writer XLSXW_1)
    attributes: id string(200), _not_found_err_msg string(200), format string(200)
AttributeExposer_9
    ATTR_TABLE = category{},
    -> AttributeRemover_4
Note: Suppression de la liste temporaire
AttributeRemover_4
    LIST_ATTRS = category{}
    -> MANUAL_GEOSPATIAL_SETTER_NG [DATA_INPUT]
MANUAL_GEOSPATIAL_SETTER_NG
    FEATURE_TYPE = UnmappedGeoData_NB
    IN_CSV_LOOKUP_TABLES_DIR = $(IN_CSV_LOOKUP_TABLES_DIR)
    P-T_ABBR = $(P-T_ABBR)
    GEOSPATIAL -> AttributeCreator_13
    NON-GEOSPATIAL -> AttributeCreator_14
    UNMAPPED_DATA -> UNMAPPED_DATA (writer XLSXW_1)
Note: _typedataset = GEO
AttributeCreator_13
    ATTR_TABLE = SET_TO _typedataset (varchar(200)) = GEO
    -> TestFilter
Note: _typedataset = NONGEO
AttributeCreator_14
    ATTR_TABLE = SET_TO _typedataset (varchar(200)) = NONGEO
    -> TestFilter_2
UNMAPPED_DATA (writer XLSXW_1)
    attributes: id string(200), title string(200), notes string(200)

Bookmark: Adding spatial type manually
AttributeExposer_4
    ATTR_TABLE = id,,resource.id,
    -> AttributeCreator_3
AttributeCreator_3
    ATTR_TABLE = SET_TO id_temp (varchar(200)) = @Value(id)
    -> AttributeCreator_4
AttributeCreator_4
    ATTR_TABLE = SET_TO id (varchar(200)) = @Value(resource.id)
    -> SPATIAL_TYPE_MAPPER_NG [DATA_INPUT]
SPATIAL_TYPE_MAPPER_NG
    FEATURE_TYPE = SpatialType_NB
    IN_CSV_LOOKUP_TABLES_DIR = $(IN_CSV_LOOKUP_TABLES_DIR)
    P-T_ABBR = $(P-T_ABBR)
    DATA_OUTPUT_FAILED -> AttributeExposer_28
    DATA_OUTPUT_PASSED -> AttributeExposer_22

Bookmark: Samples or full content
TestFilter_3
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction
    SAMPLES FEATURES -> Sampler
Sampler
    MODE = ORIGINAL
    RATE = $(SAMPLE_SIZE)
    SAMPLE_TYPE_MULTIPLIER = -1
    SAMPLE_MODE = No
    SAMPLE_TYPE_LONG = First N Features
    SAMPLED -> Junction

Bookmark: Metadata Value Mapping
Note: Topic
METADATA_VALUE_MAPPER_NG
    ATT_TO_MAP = category
    CODE_REFRESH = NO
    ENGLISH_REFRESH = YES
    ERROR_NOT_MAPPED = YES
    FEATURE_TYPE = Topic
    FRENCH_REFRESH = NO
    IN_CSV_LOOKUP_TABLES_DIR = $(IN_CSV_LOOKUP_TABLES_DIR)
    P-T_ABBR = $(P-T_ABBR)
    -> METADATA_VALUE_MAPPER_NG_2 [DATA_INPUT]
Note: Role
METADATA_VALUE_MAPPER_NG_2
    ATT_TO_MAP = contacts{}.role
    CODE_REFRESH = YES
    ENGLISH_REFRESH = YES
    ERROR_NOT_MAPPED = YES
    FEATURE_TYPE = Role
    FRENCH_REFRESH = YES
    IN_CSV_LOOKUP_TABLES_DIR = $(IN_CSV_LOOKUP_TABLES_DIR)
    P-T_ABBR = $(P-T_ABBR)
    -> METADATA_VALUE_MAPPER_NG_3 [DATA_INPUT]
Note: Update
METADATA_VALUE_MAPPER_NG_3
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_VALUE_MAPPER_NG_4 [DATA_INPUT]
Note: Progress
METADATA_VALUE_MAPPER_NG_4
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_5 [DATA_INPUT]
Note: SpatialRepresentation
METADATA_VALUE_MAPPER_NG_5
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_FORMAT_MAPPER_NG [DATA_INPUT]
Note: Format
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_Geo (writer XLSXW_1)
    -> METADATA_VALUE_MAPPER_ERROR_MANAGER
UNKNOWN_MIME_TYPE_Geo (writer XLSXW_1)
    attributes: _unknown_mime_type string(8), _url_validation string(8), id string(8)
METADATA_VALUE_MAPPER_ERROR_MANAGER
    ERROR_OUTPUT -> METADATA_MAPPING_ERRORS_GEO (writer XLSXW_1)
    DATA_OUTPUT -> AttributeRemover_6
METADATA_MAPPING_ERRORS_GEO (writer XLSXW_1)
    attributes: id string(200), error string(200)
Note: Removing error list
AttributeRemover_6
    LIST_ATTRS = mapping_errors{}
    -> RESOURCE_NAME_UNDERSCORE_REMOVER

Bookmark: Remove all underscores from resources{}.name attributes
RESOURCE_NAME_UNDERSCORE_REMOVER
    DATA_OUTPUT -> REMOVE_BROKEN_URL_WMS_ESRI_REST

Bookmark: Drop Broken Web Services
REMOVE_BROKEN_URL_WMS_ESRI_REST
    URL_VALIDATION = Yes
    -> WMS_REST_LANGUAGE_FORMATTER
    FAULTY_URL_OUTPUT -> MAP_SERVICE_URL_ERRORMAP (writer XLSXW_1)
MAP_SERVICE_URL_ERRORMAP (writer XLSXW_1)
    attributes: id string(200), url string(200), format string(200), _url_failure_message string(20)

Bookmark: HNAP RULES
WMS_REST_LANGUAGE_FORMATTER
    -> DUPLICATE_SERVICE_REMOVER
DUPLICATE_SERVICE_REMOVER
    -> GMD_SECTION_DATA_EXTRACTION
GMD_SECTION_DATA_EXTRACTION
    -> AttributeCreator

Bookmark: Configuring publishing info
AttributeCreator
    ATTR_TABLE = SET_TO csw_url (varchar(200)) = $(FORCED_PYCSW_URL)
    -> ATTRIBUTE_MANAGER_NG_7
AttributeExposer_32
    ATTR_TABLE = search_criteria_pycsw,,csw_url,,record_last_modified,,id,
    -> METADATA_DELTA_FINDER_GEN
METADATA_DELTA_FINDER_GEN
    ATTR_DATE_MODIFIED = record_last_modified
    CSW_FILTER = @Value(search_criteria_pycsw)
    LOCAL_SOURCE = $(LOCAL_SOURCE_METADATA_DELTA_FINDER)
    METADATA_OVERWRITE = $(METADATA_OVERWRITE)
    METADATA_TYPE = XML-HNAP
    SOURCE_DIRECTORY = $(OUT_XML_LOCAL_DIR)
    SOURCE_URL = @Value(csw_url)
    VALIDATE_INSERT_PCT = $(VALIDATE_INSERT_PCT_XML)
    YAML_FILE = $(IN_OUT_WORKING_DIR)\LOOKUP_TABLES\$(P-T_ABBR)\metadata_delta_finder_$(P-T_ABBR)_geo.yaml
    Statistics -> StatisticsCalculator_Summary
    Update -> Junction_4
    Insert -> Junction_4
    Delete -> AttributeExposer_23
StatisticsCalculator_Summary: Logger
    LOG_FEATURE = NONE
    MAXFEATS = 20
    MESSAGE:
      ************************
      **** GEO Unchanged Report ****
      ************************

      @Value(_real_count) features were unchanged

      ************************
      ************************
      ************************
    SEVERITY = INFO
AttributeExposer_23
    ATTR_TABLE = id,,timestamp,
    -> DELETEDRECORDS_GEO (writer XLSXW_1)

Bookmark: Listes Metadata_delta_finder
ATTRIBUTE_MANAGER_NG_7
    IN_YAML_TEXT:
      spatialref{0}.projection_name:
         action: attribute_not_null
         attr2set: default_projection_name
      spatialref{0}.projection_system:
         action: attribute_not_null
         attr2set: default_reference_system
      spatialref{0}.projection_system_version:
         action: attribute_not_null
         attr2set: default_projection_system_version
      distributionList{0}.format_version:
         action: attribute_not_null
         attr2set: distribution_format_version
      resources{0}.language:
         action: attribute_not_null
         attr2set: transfer_desc_locale_default
      contacts{0}.p-t_entity:
         action: attribute_not_null
         attr2set: p-t_entity
      contacts{0}.sector:
         action: attribute_not_null
         attr2set: sector
      contacts{0}.p-t_entity_fr:
         action: attribute_not_null
         attr2set: p-t_entity_fr
      contacts{0}.sector_fr:
         action: attribute_not_null
         attr2set: sector_fr
      iso_topic{0}.topic_value:
         action: attribute_not_null
         attr2set: category
    -> ATTRIBUTE_MANAGER_NG_8
ATTRIBUTE_MANAGER_NG_8
    IN_YAML_TEXT:
      spatialref{}.projection_name:
         action: attribute_not_null
         attr2set: default_projection_name
      spatialref{}.projection_system:
         action: attribute_not_null
         attr2set: default_reference_system
      spatialref{}.projection_system_version:
         action: attribute_not_null
         attr2set: default_projection_system_version
      distributionList{}.format_version:
         action: attribute_not_null
         attr2set: distribution_format_version
      resources{}.language:
         action: attribute_not_null
         attr2set: transfer_desc_locale_default
      contacts{}.p-t_entity:
         action: attribute_not_null
         attr2set: p-t_entity
      contacts{}.sector:
         action: attribute_not_null
         attr2set: sector
      contacts{}.p-t_entity_fr:
         action: attribute_not_null
         attr2set: p-t_entity_fr
      contacts{}.sector_fr:
         action: attribute_not_null
         attr2set: sector_fr
      iso_topic{}.topic_value:
         action: attribute_not_null
         attr2set: category
    -> AttributeExposer_32

Bookmark: AWS Translation
Note: English to french / notes, / title, / tags_en / resources name
AWS_TRANSLATE_6
    ACTIVATE_TRANSLATION = $(ACTIVATE_TRANSLATION)
    ATTR_2_TRANSLATE = notes,title
    ATTR_LIST_2_TRANSLATE = resources{}.name,tags{}.display_name
    MODE = English-->French
    -> AttributeExposer_15
    TRANSLATION_PROBLEM -> AttributeExposer_29
AttributeExposer_29
    ATTR_TABLE = id,,title,
    -> TRANSLATION_PROBLEMS_GEO (writer XLSXW_1)

Bookmark: Rebuilding tags list
AttributeExposer_15
    ATTR_TABLE = tags{}.display_name_en,,tags{}.display_name_fr,
    -> PythonCaller_5
PythonCaller_5
    PYTHONSOURCE:
      import fme
      import fmeobjects
      from Python.FME_utils import FME_utils

      # Template Function interface:
      # When using this function, make sure its name is set as the value of
      # the 'Class or Function to Process Features' transformer parameter
      def FeatureProcessor(feature):
          i=0

          max_index_en=FME_utils.max_index_attribute_list(feature,'tags{}.display_name_en')
          for j in range(max_index_en+1):
              feature.setAttribute('tags{%i}.display_name_en_lower'%(i),feature.getAttribute('tags{%i}.display_name_en'%(j)).lower())
              feature.setAttribute('tags{%i}.display_name_fr_lower'%(i),feature.getAttribute('tags{%i}.display_name_fr'%(j)).lower())
              i=i+1
    PYTHONSYMBOL = FeatureProcessor
    -> AttributeExposer_21
AttributeExposer_21
    ATTR_TABLE = tags{}.display_name_en_lower,,tags{}.display_name_fr_lower,
    -> ListDuplicateRemover_5
ListDuplicateRemover_5
    SRC_LIST = tags{}.display_name_en_lower
    -> ListDuplicateRemover_6
ListDuplicateRemover_6
    SRC_LIST = tags{}.display_name_fr_lower
    -> ATTRIBUTE_UNEXPOSER
ATTRIBUTE_UNEXPOSER
    -> XML_PUBLISHER_NG

Bookmark: XML CREATION AND WRITING
XML_PUBLISHER_NG
    FEATURE_TYPE = Config_NB
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> INVALID_METADATA (writer XLSXW_1)
    UPDATE_FAILED -> text_line (writer TEXTLINE_2)

Bookmark: Samples or full content
TestFilter_4
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_2
    SAMPLES FEATURES -> Sampler_2
Sampler_2
    MODE = ORIGINAL
    RATE = $(SAMPLE_SIZE)
    SAMPLE_TYPE_MULTIPLIER = -1
    SAMPLE_MODE = No
    SAMPLE_TYPE_LONG = First N Features
    SAMPLED -> Junction_2

Bookmark: Metadata Value Mapping - NONGEO
Note: Gestion des attributs
ATTRIBUTE_MANAGER_NG_6
    IN_YAML_TEXT:
      # Create a new tbs_topic attribute
      tbs_topic:
          action: attribute_overwrite
          attr2set: category

      # Create a new tbs_subject attribute
      tbs_subject:
          action: attribute_overwrite
          attr2set: category
    -> METADATA_VALUE_MAPPER_NG_6 [DATA_INPUT]
Note: UpdateFrequency_TBS
METADATA_VALUE_MAPPER_NG_8
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> METADATA_FORMAT_MAPPER_NG_2 [DATA_INPUT]
Note: Format_TBS
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_NoneGeo (writer XLSXW_1)
    -> METADATA_VALUE_MAPPER_ERROR_MANAGER_2
UNKNOWN_MIME_TYPE_NoneGeo (writer XLSXW_1)
    attributes: _unknown_mime_type string(8), _url_validation string(8), id string(8)
METADATA_VALUE_MAPPER_ERROR_MANAGER_2
    ERROR_OUTPUT -> ATTRIBUTE_MAPPING_ERRORS00_NONGEO (writer XLSXW_1)
    DATA_OUTPUT -> AttributeExposer_16
ATTRIBUTE_MAPPING_ERRORS00_NONGEO (writer XLSXW_1)
    attributes: id string(200), error string(200)

Bookmark: Generating Tbs Topic based on category
Note: Topic_TBS
METADATA_VALUE_MAPPER_NG_6
    ATT_TO_MAP = tbs_topic
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUP_TABLES_DIR)
    P-T_ABBR = $(P-T_ABBR)
    -> METADATA_VALUE_MAPPER_NG_7 [DATA_INPUT]

Bookmark: Generating TBS_SUBJECT list based on category
Note: Subject_TBS
METADATA_VALUE_MAPPER_NG_7
    ATT_TO_MAP = tbs_subject
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUP_TABLES_DIR)
    P-T_ABBR = $(P-T_ABBR)
    -> AttributeExposer_10
AttributeExposer_10
    ATTR_TABLE = TBS_Subject{}.value,
    -> METADATA_VALUE_MAPPER_NG_8 [DATA_INPUT]

Bookmark: Default value for resources language
AttributeExposer_16
    ATTR_TABLE = resources{},,default_res_language,
    -> ListElementCounter
ListElementCounter
    CNT_ATTR = _element_count
    LIST_NAME = resources{}
    -> PythonCaller
PythonCaller
    PYTHONSOURCE:
      import fme
      import fmeobjects
      # Template Class Interface:
      # When using this class, make sure its name is set as the value of
      # the 'Class or Function to Process Features' transformer parameter
      def FeatureProcessor(feature):
          split_list = str(feature.getAttribute('default_resource_language')).split(";")
          resource_language = '['

          for i in range(len(split_list)):
              if i == len(split_list) - 1:
                  resource_language = resource_language + '"' + split_list[i] + '"'
              else:
                  resource_language = resource_language + '"' + split_list[i] + '",'

          resource_language = resource_language + ']'

          for i in range(int(feature.getAttribute('_element_count'))):
              feature.setAttribute('resources{%d}.language_list'%(i),str(resource_language))
    PYTHONSYMBOL = FeatureProcessor
    -> AttributeRemover_10
AttributeRemover_10
    REMOVE_ATTRS = _element_count
    -> AttributeExposer_2

Bookmark: Delta Finder -NONGEO
METADATA_DELTA_FINDER_GEN_2
    ATTR_DATE_MODIFIED = record_last_modified
    LOCAL_SOURCE = Yes
    METADATA_OVERWRITE = $(METADATA_OVERWRITE)
    METADATA_TYPE = JSON-CKANExtCa
    SOURCE_DIRECTORY = $(OUT_JSON_LOCAL_DIR)
    VALIDATE_INSERT_PCT = $(VALIDATE_INSERT_PCT_JSON)
    YAML_FILE = $(IN_OUT_WORKING_DIR)\LOOKUP_TABLES\$(P-T_ABBR)\metadata_delta_finder_$(P-T_ABBR)_non_geo.yaml
    Statistics -> StatisticsCalculator_Summary_3
    Update -> Junction_3
    Insert -> Junction_3
    Delete -> AttributeExposer_31
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
AttributeExposer_31
    ATTR_TABLE = id,,title,
    -> DELETED_RECORDS_NONE_GEO (writer XLSXW_1)

Bookmark: AWS Translation
Note: English to french / notes, / title, / tags_en / resources name
AWS_TRANSLATE_2
    ACTIVATE_TRANSLATION = $(ACTIVATE_TRANSLATION)
    ATTR_2_TRANSLATE = notes,title
    ATTR_LIST_2_TRANSLATE = resources{}.name,tags{}.display_name
    MODE = English-->French
    -> AttributeExposer_6
    TRANSLATION_PROBLEM -> AttributeExposer_30
AttributeExposer_30
    ATTR_TABLE = id,,title,
    -> TRANSLATION_PROBLEMS_NONE_GEO (writer XLSXW_1)

Bookmark: Rebuilding tags list
AttributeExposer_6
    ATTR_TABLE = tags{}.display_name_en,,tags{}.display_name_fr,
    -> PythonCaller_2
PythonCaller_2
    PYTHONSOURCE:
      import fme
      import fmeobjects
      from Python.FME_utils import FME_utils

      # Template Function interface:
      # When using this function, make sure its name is set as the value of
      # the 'Class or Function to Process Features' transformer parameter
      def FeatureProcessor(feature):
          i=0

          max_index_en=FME_utils.max_index_attribute_list(feature,'tags{}.display_name_en')
          for j in range(max_index_en+1):
              feature.setAttribute('tags{%i}.display_name_en_lower'%(i),feature.getAttribute('tags{%i}.display_name_en'%(j)).lower())
              feature.setAttribute('tags{%i}.display_name_fr_lower'%(i),feature.getAttribute('tags{%i}.display_name_fr'%(j)).lower())
              i=i+1
    PYTHONSYMBOL = FeatureProcessor
    -> AttributeExposer_14
AttributeExposer_14
    ATTR_TABLE = tags{}.display_name_en_lower,,tags{}.display_name_fr_lower,
    -> ListDuplicateRemover_3
ListDuplicateRemover_3
    SRC_LIST = tags{}.display_name_en_lower
    -> ListDuplicateRemover_4
ListDuplicateRemover_4
    SRC_LIST = tags{}.display_name_fr_lower
    -> ATTRIBUTE_UNEXPOSER_3
ATTRIBUTE_UNEXPOSER_3
    -> JSON_PUBLISHER_NG

Bookmark: JSON CREATION AND WRITING
Note: Config_JSON_NB
JSON_PUBLISHER_NG
    FEATURE_TYPE = Config_JSON_NB
    IN_CSV_LOOKUP_TABLES_DIR = $(IN_CSV_LOOKUP_TABLES_DIR)
    JSON_RESOURCE_TEMPLATE = $(IN_TBS_JSON_TEMPLATE_DIR)/TBS_RESOURCES_TEMPLATE_NG.json
    JSON_ROOT_TEMPLATE = $(IN_TBS_JSON_TEMPLATE_DIR)/TBS_ROOT_TEMPLATE_NG.json
    Keywords_EN = tags{}.display_name
    Keywords_FR = tags{}.display_name_fr
    P-T_ABBR = $(P-T_ABBR)
    Subject_LIST = TBS_Subject{}.value
    Topic_LIST = TBS_Topic{}.value
    OUTPUT_LOCAL -> AttributeExposer_17
AttributeExposer_17
    ATTR_TABLE = json_file,
    -> text_line (writer TEXTLINE_4)
text_line (writer TEXTLINE_4)
    attributes: text_line_data buffer
