FME workspace BC_PROD.fmw
Title: BC_PROD
Description: Description 
This workbench read and trasform all the metadata for the province of British Columbia (BC)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
SAMPLE_SIZE: Number of features to process. Zero (0) means process all the features. A number n greater than 0 means sample or process only the first n features.
URL_VALIDATION : Indicates to validate or not created URL. (Should be Yes for prod)
VALIDATE_INSERT_PCT :Indicates to valide insert percentage. 75 % or less insert/update record  (Should be Yes for prod)
History: Original version,Unknown,Unknown,Terminate Geo processing. Develop Non geo processing.,5/7/2022,Daniel Pilon,
Startup Python:
      import sys
      import fme
      try:
          if fme.macroValues['FME_SHAREDRESOURCE_DATA']:
              new_path='%s\PT_Harvester\Python'%(fme.macroValues['FME_SHAREDRESOURCE_DATA'])

              print ('Ajout de %s dans le path '%(new_path))
              sys.path += [new_path]


      except:
          raise

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = NO
- SAMPLE_SIZE = 0
- IN_OUT_WORKING_DIR = $(FME_SHAREDRESOURCE_DATA)\PT_Harvester
- URL_VALIDATION = Yes
- VALIDATE_INSERT_PCT_JSON = Yes
- VALIDATE_INSERT_PCT_XML = Yes
- IN_CSV_LOOKUP_TABLES_DIR = $(IN_OUT_WORKING_DIR)\LOOKUP_TABLES   # DEFAULT_IN_CSV_LOOKUP_TABLES_DIR
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Flow Data Directory

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_LOCAL_DIR)

Note: Maps data collection start and end dates
TEMPORAL_EXTENTS_MAPPER
    -> URL_HTTPS_MAKER [UUIDGenerator_Input]
AttributeExposer_3
    ATTR_TABLE = default_contact_email,
    -> PythonCaller_3
Note: Extraction des topics à partir des ressources
PythonCaller_3
    NEW_ATTRIBUTES = topic{}.value buffer
    PYTHONSOURCE:
      import fme
      import fmeobjects
      from Python.FME_utils import FME_utils
      # Template Function interface:
      # When using this function, make sure its name is set as the value of
      # the 'Class or Function to Process Features' transformer parameter
      def processFeature(feature):

          topic=[]
          max_index=FME_utils.max_index_attribute_list(feature,'resources{}')
          for j in range(max_index+1):
              items=feature.getAttribute('resources{%i}.iso_topic_category{}'%(j))


              if items:
                  for elem in items:
                      if elem:

                          topic.append(elem)


          if topic:

              topic_unique=list(dict.fromkeys(topic))

              i=0
              for items in topic_unique:
                  feature.setAttribute('topic{%i}.value'%(i),items)
                  i+=1



          else:
               topic_extra=''

               #Parcourir la liste des extras pour trouver l'extra de type sector.

               max_index=FME_utils.max_index_attribute_list(feature,'extras{}')
               for j in range(max_index+1):
                   if feature.getAttribute('extras{%i}.key'%(j))=='sector':
                       topic_extra=feature.getAttribute('extras{%i}.value'%(j))

               if topic_extra:
                   feature.setAttribute('topic{0}.value',topic_extra)
               else:
                   feature.setAttribute('topic{0}.value',feature.getAttribute('default_topic'))
    PYTHONSYMBOL = processFeature
    -> AttributeExposer_21
Junction
    -> PythonCaller_5
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
INVALID_METADATA (writer XLSXW_1)
    attributes: id auto(20)
Junction_2
    -> METADATA_VALUE_MAPPER_NG_4 [DATA_INPUT]
Note: CSV JSON config file to map BC attributes to those required by the JSON templates
JSON_PUBLISHER_NG
    FEATURE_TYPE = JSON_CONFIG_BC
    IN_CSV_LOOKUP_TABLES_DIR = $(IN_CSV_LOOKUP_TABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.display_name
    Keywords_FR = tags{}.display_name_fr
    P-T_ABBR = $(P-T_ABBR)
    Subject_LIST = subject{}.value
    Topic_LIST = topic{}.value
    OUTPUT_LOCAL -> AttributeExposer_4
AttributeExposer_4
    ATTR_TABLE = json_file,,id,
    -> AttributeCreator_2
AttributeCreator_2
    ATTR_TABLE = SET_TO text_line_data (varchar(200)) = @Value(json_file)
    -> text_line (writer TEXTLINE_4)
Note: Write the JSON files
text_line (writer TEXTLINE_4)
    attributes: text_line_data buffer

Bookmark: Reading BC Geoportal datasets
Note: Start the process
Creator
    GEOMTYPE = Geometry Object
    NUM = 1
    CREATED -> Tester_3
Tester_3
    BOOL_OP = OR
    TEST_CLAUSE = TEST $(CATALOGUE_READER_SELECT) = Yes
    TEST_MODE = TEST
    PASSED -> Catalogue_Reader
    FAILED -> FeatureReader [INITIATOR]
Note: Reading BC Server CKAN-API
Catalogue_Reader: Catalogue Reader
    CUSTOM_CSW_LIST_NAME = DefaultNoList{}
    CUSTOM_URL = https://catalogue.data.gov.bc.ca/api/3/action
    SOURCE_URL = Manuel
    Résultats -> Junction_8
Note: Reading FFS file
FeatureReader
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> Junction_8

Bookmark: Prétraitement pour la validation des ressources
Note: Il n'y a pas d'url dans la ressource BC Geographic Warehouse Custom Download. / On construit le lien vers le BC Geographic Warehouse Custom Download / https://catalogue.data.gov.bc.ca/dataset/<dateset_name>/resource/<resource_id>
Junction_8
    -> PythonCaller_6
PythonCaller_6
    PYTHONSOURCE:
      import fme
      import fmeobjects
      from Python.FME_utils import FME_utils
      # Template Function interface:
      # When using this function, make sure its name is set as the value of
      # the 'Class or Function to Process Features' transformer parameter
      def processFeature(feature):

          max_index=FME_utils.max_index_attribute_list(feature,'resources{}')
          for j in range(max_index+1):
              if not feature.getAttribute('resources{%i}.url'%(j)) and feature.getAttribute('resources{%i}.name'%(j))=='BC Geographic Warehouse Custom Download':
                  # Il n'y a pas d'url, on la construit et on la valide
                  bc_warehouse=r'https://catalogue.data.gov.bc.ca/dataset/%s/resource/%s'%(feature.getAttribute('name'),feature.getAttribute('resources{%i}.id'%(j)))

                  #On ne valide pas l'url car même si ça marche pas, on recoit une erreur 200
                  feature.setAttribute('resources{%i}.url'%(j),bc_warehouse)
                  feature.setAttribute('resources{%i}.format'%(j),'HTML')

                  #On met vide l'object name pour ne pas interférer avec le code plus tard
                  feature.setAttribute('resources{%i}.object_name'%(j),'')
    PYTHONSYMBOL = processFeature
    -> ATTRIBUTE_VALUE_TEXT_CLEANER

Bookmark: Attribute Validation
Note: Basic edition (trimming, remove tab, cr/lf) to all fields
ATTRIBUTE_VALUE_TEXT_CLEANER
    -> RESOURCES_VALIDATOR_3
Note: Retrait des ressources sans lien
RESOURCES_VALIDATOR_3
    -> FORMAT_VALIDATOR
Note: Verfication if URL is valid WMS call for WMS formats
FORMAT_VALIDATOR
    -> DEFAULT_ATTRIBUTE_MAPPER_NG

Bookmark: Data extraction
Note: Add some defaults attribute values
DEFAULT_ATTRIBUTE_MAPPER_NG
    FEATURE_TYPE = Default_BC
    IN_CSV_LOOKUP_TABLES_DIR = $(IN_CSV_LOOKUP_TABLES_DIR)
    P-T_ABBR = $(P-T_ABBR)
    -> ATTRIBUTE_MANAGER_NG
Note: Manage empty attributes
ATTRIBUTE_MANAGER_NG
    IN_YAML_TEXT:
      resources{0}.projection_name:
          action: attribute_not_null
          attr2set: default_reference_system
      #
      resources{}.name:
          action: attribute_not_null
          attr2set: resources{}.description
      #
      resources{0}.resource_update_cycle:
          action: attribute_not_null
          attr2set: default_resource_update_cycle
      #
      #
      resources{0}.language:
          action: text_not_null
          attr2set: eng
      license_title:
         action: attribute_not_null
         attr2set: default_license_title

      resources_status:
         action: attribute_not_null
         attr2set: default_progress_code

      record_create_date:
         action: attribute_not_null
         attr2set: record_publish_date
    -> ATTRIBUTE_MANAGER_NG_2
Note: Manage empty attributes pouir les listes
ATTRIBUTE_MANAGER_NG_2
    IN_YAML_TEXT:
      resources{}.projection_name:
          action: attribute_not_null
          attr2set: default_reference_system
      #
      resources{}.resource_update_cycle:
          action: attribute_not_null
          attr2set: default_resource_update_cycle
      #
      #
      resources{}.language:
          action: text_not_null
          attr2set: eng
    -> AttributeExposer_2
Note: Correction des noms de ressources. On prend l'object name lorsque présent sinon c'est name
PythonCaller_2
    PYTHONSOURCE:
      import fme
      import fmeobjects
      from Python.FME_utils import FME_utils
      # Template Function interface:
      # When using this function, make sure its name is set as the value of
      # the 'Class or Function to Process Features' transformer parameter
      def processFeature(feature):
          max_index=FME_utils.max_index_attribute_list(feature,'resources{}')
          for j in range(max_index+1):
              if feature.getAttribute('resources{%i}.object_name'%(j)):
                  try:
                      #extraction du nom de la couche sans le schema
                      value=feature.getAttribute('resources{%i}.object_name'%(j)).split('.')[1]
                  except:
                      value=feature.getAttribute('resources{%i}.object_name'%(j))

                  feature.setAttribute('resources{%i}.name'%(j),value)


      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> AttributeExposer_18

Bookmark: Filtering and convertion to inhouse model.
AttributeExposer_2
    ATTR_TABLE = license_title,
    -> LICENSE_FILTER_NG
Note: Sort the records based on the type of licence (Open source licence or otther)
LICENSE_FILTER_NG
    FEATURE_TYPE = License_BC
    IN_CSV_LOOKUP_TABLES_DIR = $(IN_CSV_LOOKUP_TABLES_DIR)
    LICENSE_ATT = @Value(license_title)
    P-T_ABBR = $(P-T_ABBR)
    LICENSE_FILTER_PASSED -> PythonCaller_2
    UNKNOWN_LICENSE -> UNKNOWN_LICENCE (writer XLSXW_1)
UNKNOWN_LICENCE (writer XLSXW_1)
    attributes: license_id string(200), id string(200)

Bookmark: Ajustement des dates
AttributeExposer_18
    ATTR_TABLE = record_publish_date,,record_create_date,,record_last_modified,
    -> DateTimeConverter
Note: Formats all date fields to ISO yyyy-mm-dd
DateTimeConverter
    DATETIME_ATTR = record_publish_date record_last_modified record_create_date
    OUT_FORMAT = %Y-%m-%d
    PASSTHROUGH = NO
    REPAIR_INPUT = YES
    -> EMPTY_FORMAT_MAPPER_NG [DATA_INPUT]
    <REJECTED> -> AttributeExposer_19
AttributeExposer_19
    ATTR_TABLE = title,,id,
    -> AttributeCreator
AttributeCreator
    ATTR_TABLE = SET_TO error (varchar(200)) = Erreur de format de date. Vérifier record_publish_date , record_create_date , record_last_modified
    -> date_issue (writer XLSXW_1)
date_issue (writer XLSXW_1)
    attributes: id string(200), error string(200), title string(200)

Bookmark: Add geoportal weblink
Note: Check if resources{}.format="other" can be modified into a more meaningful format value
EMPTY_FORMAT_MAPPER_NG
    CSV_FORMAT = Format
    CSV_MIME_TYPE = Mime_type
    IN_CSV_LOOKUP_TABLES_DIR = $(IN_CSV_LOOKUP_TABLES_DIR)
    P-T_ABBR = $(P-T_ABBR)
    URL_VALIDATION = $(URL_VALIDATION)
    DATA_OUTPUT -> AttributeExposer_5
    UNKNOWN_MIME_TYPE -> UNKNOWN_MIME_TYPE (writer XLSXW_1)
AttributeExposer_5
    ATTR_TABLE = name,
    -> GEOPORTAL_WEBLINK_ADDER_NG
Note: Add an html resource
GEOPORTAL_WEBLINK_ADDER_NG
    FEATURE_TYPE = GeoportalWeblink_BC
    IN_CSV_LOOKUP_TABLES_DIR = $(IN_CSV_LOOKUP_TABLES_DIR)
    P-T_ABBR = $(P-T_ABBR)
    URL_VALIDATION = $(URL_VALIDATION)
    WEBLINK_WILDCARD = @Value(name)
    -> TEMPORAL_EXTENTS_MAPPER
UNKNOWN_MIME_TYPE (writer XLSXW_1)
    attributes: _unknown_mime_type string(200), _url_validation string(200), id string(200)

Bookmark: https maker
URL_HTTPS_MAKER
    P-T_ABBR = $(P-T_ABBR)
    URL_VALIDATION = $(URL_VALIDATION)
    -> AttributeExposer_3

Bookmark: Gestion de l'update cycle
AttributeExposer_21
    ATTR_TABLE = resources{}.resource_update_cycle,
    -> ListCopier_2
Note: Copie de la liste des ressources
ListCopier_2
    DEST_LIST = update_cycle
    SRC_LIST = resources{}
    -> ListDuplicateRemover_4
Note: Retrait des doublons au niveau de resource_update_cyle
ListDuplicateRemover_4
    SRC_LIST = update_cycle{}.resource_update_cycle
    -> ListSorter
Note: L'uptdate cycle pour les données de BC est directement. Par contre, au niveau du HNAP, c'est une seule valeur. / On extrait les valeurs uniques et lorsqu'il y a plus d'une valeur, la table de corrélation va correler avec une valeur la plus logique déterminée manuellement
ListSorter
    ORDER = Ascending
    SRC_LIST = update_cycle{}.resource_update_cycle
    TYPE = Alphabetic
    -> ListConcatenator
Note: Concatenation en update_frequency
ListConcatenator
    DROP_EMPTY_PARTS = No
    LIST_ATTR = update_cycle{}.resource_update_cycle
    SEP = -
    VAL_ATTR = update_cycle
    -> AttributeRemover_2
Note: Suppression de liste temporaire
AttributeRemover_2
    LIST_ATTRS = update_cycle{}
    -> GEO_NONE_GEO_SELECTOR

Bookmark: Spatial data type management
Note: Sort the features into 2 categories: GEO and NONE GEO
GEO_NONE_GEO_SELECTOR
    CSV_FILE_NAME = GeospatialValidation
    CSV_PATH = $(IN_CSV_LOOKUP_TABLES_DIR)
    CSV_PROVINCE = $(P-T_ABBR)
    YAML_DIRECTIVES:
      resources{}.format:
          domain: lookup_table_format
          spatial_type: if_null_overwrite
          not_found: log
          search_type: equals
      #
      resources{}.bcdc_type:
          domain: [spatial,geographic]
          spatial_type: no_overwrite
          not_found: no_log
          search_type: contains
    GEOSPATIAL -> SPATIAL_TYPE_MAPPER_NG [DATA_INPUT]
    NONE_GEOSPATIAL -> MANUAL_GEOSPATIAL_SETTER_NG [DATA_INPUT]
    LOG_ERROR -> GEOSPATIAL_FORMAT_NOT_MAPPED (writer XLSXW_1)
Note: Determine the spatial representation type of datasets for each feature
SPATIAL_TYPE_MAPPER_NG
    FEATURE_TYPE = UUID_Spatial_BC
    IN_CSV_LOOKUP_TABLES_DIR = $(IN_CSV_LOOKUP_TABLES_DIR)
    P-T_ABBR = $(P-T_ABBR)
    DATA_OUTPUT_FAILED -> AttributeExposer_16
    DATA_OUTPUT_PASSED -> Junction_3
AttributeExposer_16
    ATTR_TABLE = id,,title,,notes,
    -> SPATIAL_TYPE_NOT_MAPPED (writer XLSXW_1)
SPATIAL_TYPE_NOT_MAPPED (writer XLSXW_1)
    attributes: id auto(20), title auto(20), notes auto(20)
GEOSPATIAL_FORMAT_NOT_MAPPED (writer XLSXW_1)
    attributes: id string(200), format string(200)
Note: Use CSV table to determine the spatial representation type of datasets
MANUAL_GEOSPATIAL_SETTER_NG
    FEATURE_TYPE = UnmappedGeoData_BC
    IN_CSV_LOOKUP_TABLES_DIR = $(IN_CSV_LOOKUP_TABLES_DIR)
    P-T_ABBR = $(P-T_ABBR)
    GEOSPATIAL -> Junction_3
    NON-GEOSPATIAL -> Tester_4
    UNMAPPED_DATA -> UNMAPPED_DATA (writer XLSXW_1)
Junction_3
    -> Tester_7
UNMAPPED_DATA (writer XLSXW_1)
    attributes: id string(200), notes string(200), title string(200)

Bookmark: Activate Geo and Sample or full content
Note: GEO activated?
Tester_7
    BOOL_OP = OR
    TEST_CLAUSE = TEST @UpperCase($(ACTIVATE_GEO)) = YES
    TEST_MODE = TEST
    PASSED -> TestFilter
TestFilter
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction
    SAMPLES FEATURES -> Sampler_3
Sampler_3
    MODE = ORIGINAL
    RATE = $(SAMPLE_SIZE)
    SAMPLE_TYPE_MULTIPLIER = -1
    SAMPLE_MODE = No
    SAMPLE_TYPE_LONG = First N Features
    SAMPLED -> Junction

Bookmark: Attribute value mapper
PythonCaller_5
    PYTHONSOURCE:
      import fme
      import fmeobjects
      import json
      from Python.FME_utils import FME_utils
      # Template Function interface:
      # When using this function, make sure its name is set as the value of
      # the 'Class or Function to Process Features' transformer parameter
      def processFeature(feature):
         #Creation du BBOX à mettre jour
         north=-90 # Le nord sera plus grand que  -90, donc mis à jour
         south=90 # Le sud sera plus petit que 90, donc mis à jour
         east=-180 # East sera plus grand que -180, donc mis à jour
         west=180 # Ouest sera plus petit que 180, donc mis à jour.

         dict={}
         max_index=FME_utils.max_index_attribute_list(feature,'resources{}')
         for j in range(max_index+1):
             if feature.getAttribute('resources{%i}.geographic_extent'%(j)):
                 try:

                      temp=feature.getAttribute('resources{%i}.geographic_extent'%(j)).replace('"','').replace('(','').replace(')','').replace('\\','')
                      for items in temp.split(','):
                           key=items.split(':')[0]
                           value=float(items.split(':')[1])
                           dict[key]=value





                      if dict['north_bound_latitude'] > north:
                          north=dict['north_bound_latitude']
                      if dict['south_bound_latitude'] < south:
                          south=dict['south_bound_latitude']
                      if dict['east_bound_longitude'] > east:
                          east=dict['east_bound_longitude']
                      if dict['west_bound_longitude'] < west:
                          west=dict['west_bound_longitude']
                 except:
                      pass
         if  north != -90 and south != 90 and east != -180 and west != 180:
             # Le calcul du bbox a fonctionné, on le met en valeur
             feature.setAttribute('north_bound_latitude',north)
             feature.setAttribute('south_bound_latitude',south)
             feature.setAttribute('east_bound_longitude',east)
             feature.setAttribute('west_bound_longitude',west)
         else:
             #On met les valeurs par défaut
             feature.setAttribute('north_bound_latitude',feature.getAttribute('default_north_bound_latitude'))
             feature.setAttribute('south_bound_latitude',feature.getAttribute('default_south_bound_latitude'))
             feature.setAttribute('east_bound_longitude',feature.getAttribute('default_east_bound_longitude'))
             feature.setAttribute('west_bound_longitude',feature.getAttribute('default_west_bound_longitude'))
    PYTHONSYMBOL = processFeature
    -> PythonCaller
Note: Concatenates WMS URL's to required WMS format
PythonCaller
    PYTHONSOURCE:
      import fme
      import fmeobjects
      from Python.FME_utils import FME_utils
      #import re

      def FeatureProcessor(feature):

          id=feature.getAttribute('id')
          max_index=FME_utils.max_index_attribute_list(feature,'resources{}.url')
          for j in range(max_index+1):
              url=feature.getAttribute('resources{%i}.url'%(j))
              if 'service=WMS&request=GetCapabilities' in url:
                  object_name=feature.getAttribute('resources{%i}.object_name'%(j))
                  #object_name_url=((url.split('https://openmaps.gov.bc.ca/geo/pub/'))[1].split('/ows?service=WMS&request=GetCapabilities')[0])
                  feature.setAttribute('resources{%s}.url'%(j),r'%s&layers=pub:%s&legend_format=image/png&feature_info_type=text/plain'%(url,object_name))
    PYTHONSYMBOL = FeatureProcessor
    -> METADATA_VALUE_MAPPER_NG_3 [DATA_INPUT]
Note: This section utilizes mulitple instances of the METADATA_VALUE_MAPPER to correct values to valid English values and to add the valid French equivalents and RI_CODES where applicable. It can be utilized for mulitple metadata items by accessing custom look up tables applicable to specific items. / Turn the error mapping options and the data items to be mapped on or off by clicking on the transformer and selecting yes/no. / - ERROR_NOT_MAPPED: enables mapping of data item values that cannot be found in the lookup tables. / - ENGLISH_REFRESH: enables updating of English attribute values. / - FRENCH_REFRESH: enables updating of French attribute values. / - CODE_REFRESH: enables updating of RI_CODE values. / Enter the attribute key name by clicking on the transformer and selecting the drop down menu next to the 'att_to_map' text box and selecting the 'Open text editor...' option. Explicitly enter the attribute key name in the text editor (ie: contacts{}.role). / IMPORTANT: Do not select the 'Attribute Value' option from the drop down menu to select the attribute key name.
Note: Maps topic to HNAP standards
METADATA_VALUE_MAPPER_NG_3
    ATT_TO_MAP = topic{}.value
    CODE_REFRESH = NO
    ENGLISH_REFRESH = YES
    ERROR_NOT_MAPPED = YES
    FEATURE_TYPE = Topic
    FRENCH_REFRESH = NO
    IN_CSV_LOOKUP_TABLES_DIR = $(IN_CSV_LOOKUP_TABLES_DIR)
    P-T_ABBR = $(P-T_ABBR)
    -> METADATA_VALUE_MAPPER_NG_5 [DATA_INPUT]
Note: Maps role to HNAP standards
METADATA_VALUE_MAPPER_NG_5
    ATT_TO_MAP = contacts{}.role
    CODE_REFRESH = YES
    ENGLISH_REFRESH = YES
    ERROR_NOT_MAPPED = YES
    FEATURE_TYPE = Role
    FRENCH_REFRESH = YES
    IN_CSV_LOOKUP_TABLES_DIR = $(IN_CSV_LOOKUP_TABLES_DIR)
    P-T_ABBR = $(P-T_ABBR)
    -> METADATA_VALUE_MAPPER_NG_8 [DATA_INPUT]
Note: Maps spatial representation types to HNAP standards
METADATA_VALUE_MAPPER_NG_8
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_VALUE_MAPPER_NG_2 [DATA_INPUT]
Note: Maps reference system info to HNAP standards
METADATA_VALUE_MAPPER_NG_2
    ATT_TO_MAP = resources{}.projection_name
    CODE_REFRESH = NO
    ENGLISH_REFRESH = YES
    ERROR_NOT_MAPPED = YES
    FEATURE_TYPE = SpatialRef
    FRENCH_REFRESH = NO
    IN_CSV_LOOKUP_TABLES_DIR = $(IN_CSV_LOOKUP_TABLES_DIR)
    P-T_ABBR = $(P-T_ABBR)
    -> METADATA_VALUE_MAPPER_NG_11 [DATA_INPUT]
Note: Mapsr resource_status (progress code) to HNAP standards
METADATA_VALUE_MAPPER_NG_11
    ATT_TO_MAP = resource_status
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_10 [DATA_INPUT]
Note: Maps update cycle to HNAP standards
METADATA_VALUE_MAPPER_NG_10
    ATT_TO_MAP = update_cycle
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_FORMAT_MAPPER_NG_3 [DATA_INPUT]

Bookmark: Format value mapper
Note: Map resources.format to HNAP standards
Note: This section utilizes the METADATA_FORMAT_MAPPER to correct data format values to valid data format values and to associate and add the French and English 'Resource Type' attribute to each data format type. It accesses a custom look up table applicable to data formats. / Turn the error mapping options and the data items to be mapped on or off by clicking on the transformer and selecting yes/no. / - ERROR_NOT_MAPPED: enables mapping of data item values that cannot be found in the lookup tables. / - REAL_VALUE_REFRESH: enables updating of data format attribute values. / - RES_TYPE_FR_REFRESH: enables mapping of French resource types. / - RES_TYPE_EN_REFRESH: enables mapping of English resource types. / Enter the attribute key name by clicking on the transformer and selecting the drop down menu next to the 'att_to_map' text box and selecting the 'Open text editor...' option. Explicitly enter the attribute key name in the text editor (ie: resources{}.format). / IMPORTANT: Do not select the 'Attribute Value' option from the drop down menu to select the attribute key name.
METADATA_FORMAT_MAPPER_NG_3
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_Geo (writer XLSXW_1)
    -> METADATA_VALUE_MAPPER_ERROR_MANAGER
UNKNOWN_MIME_TYPE_Geo (writer XLSXW_1)
    attributes: _unknown_mime_type string(8), _url_validation string(8), id string(8)

Bookmark: Mapping error list creator
Note: Creates list of errors found and not corrected in mapping
METADATA_VALUE_MAPPER_ERROR_MANAGER
    ERROR_OUTPUT -> METADATA_MAPPING_ERRORS (writer XLSXW_1)
    DATA_OUTPUT -> REMOVE_BROKEN_URL_WMS_ESRI_REST
METADATA_MAPPING_ERRORS (writer XLSXW_1)
    attributes: error string(200), id string(200)

Bookmark: Data cleanup. Dropping broken web services
Note: Tests WMS/ESRI_REST resource URL's and removes them where broken
REMOVE_BROKEN_URL_WMS_ESRI_REST
    URL_VALIDATION = $(URL_VALIDATION)
    -> WMS_REST_LANGUAGE_FORMATTER
    FAULTY_URL_OUTPUT -> MAP_SERVICE_URL_ERROR (writer XLSXW_1)
MAP_SERVICE_URL_ERROR (writer XLSXW_1)
    attributes: id string(200), url string(200), format string(200), _url_failure_message string(20)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> AttributeExposer_6

Bookmark: Creation de la liste des formats
AttributeExposer_6
    ATTR_TABLE = resources{}.format,
    -> ListCopier
ListCopier
    DEST_LIST = distributionList
    SRC_LIST = resources{}
    -> ListDuplicateRemover_3
ListDuplicateRemover_3
    SRC_LIST = distributionList{}.format
    -> PythonCaller_4

Bookmark: Extraction personnalisé de l'information à partir de la liste des ressources
Note: Création de la liste projectionList pour les système de référence spatiale. / On part de la liste des ressources et on épure le projection_name / Si unknow et autre vraie valeur, on garde juste les vraies valeurs / Pas de doublons
PythonCaller_4
    NEW_ATTRIBUTES = proprojectionList{}.projection_name buffer
    PYTHONSOURCE:
      import fme
      import fmeobjects
      # Template Function interface:
      # When using this function, make sure its name is set as the value of
      # the 'Class or Function to Process Features' transformer parameter
      def processFeature(feature):
          proj=feature.getAttribute('resources{}.projection_name')

          proj=list(dict.fromkeys(proj))

          if 'unknown' in proj and len(proj)>1:
              proj.remove('unknown')

          #Construire la liste de projection à partir de proj
          i=0
          for items in proj:
              if 'EPSG' in items:
                  feature.setAttribute('projectionList{%i}.projection_system'%(i),'EPSG')
              feature.setAttribute('projectionList{%i}.projection_name'%(i),items)
              i=i+1



      # Template Class Interface:
      # When using this class, make sure its name is set as the value of
      # the 'Class or Function to Process Features' transformer parameter
      class FeatureProcessor(object):
          def __init__(self):
              pass
          def input(self,feature):
              self.pyoutput(feature)
          def close(self):
              pass
    PYTHONSYMBOL = processFeature
    -> AttributeCreator_6

Bookmark: Manges Insert/Update/delete
Note: Expose published parameter FORCED_PYCSW_URL
AttributeCreator_6
    ATTR_TABLE = SET_TO csw_url (varchar(200)) = $(FORCED_PYCSW_URL)
    -> ATTRIBUTE_MANAGER_NG_4
AttributeExposer_20
    ATTR_TABLE = search_criteria_pycsw,,csw_url,,record_last_modified,,id,
    -> METADATA_DELTA_FINDER_GEN
METADATA_DELTA_FINDER_GEN
    ATTR_DATE_MODIFIED = record_last_modified
    CSW_FILTER = @Value(search_criteria_pycsw)
    LOCAL_SOURCE = $(LOCAL_SOURCE_METADATA_DELTA_FINDER)
    METADATA_OVERWRITE = $(METADATA_OVERWRITE)
    METADATA_TYPE = XML-HNAP
    SOURCE_DIRECTORY = $(OUT_XML_LOCAL_DIR)
    SOURCE_URL = @Value(csw_url)
    VALIDATE_INSERT_PCT = $(VALIDATE_INSERT_PCT_XML)
    YAML_FILE = $(IN_CSV_LOOKUP_TABLES_DIR)\$(P-T_ABBR)\metadata_delta_finder_$(P-T_ABBR)_geo.yaml
    Statistics -> StatisticsCalculator_Summary_2
    Update -> Junction_5
    Insert -> Junction_5
    Delete -> AttributeExposer_11
AttributeExposer_11
    ATTR_TABLE = id,,title,
    -> DELETE_RECORDS_GEO (writer XLSXW_1)
DELETE_RECORDS_GEO (writer XLSXW_1)
    attributes: id string(200), title string(200)
Note: Log statistics
StatisticsCalculator_Summary_2: Logger
    LOG_FEATURE = NONE
    MAXFEATS = 20
    MESSAGE:
      ************************
      **** Geo Unchanged Report ****
      ************************

      @Value(_real_count) features were unchanged

      ************************
      ************************
      ************************
    SEVERITY = INFO
Junction_5
    -> AWS_TRANSLATE

Bookmark: Listes Metadata_delta_finder
ATTRIBUTE_MANAGER_NG_4
    IN_YAML_TEXT:
      contacts{0}.p-t_entity:
         action: attribute_not_null
         attr2set: p-t_entity
      contacts{0}.p-t_entity_fr:
         action: attribute_not_null
         attr2set: p-t_entity_fr
      distributionList{0}.format_version:
         action: attribute_not_null
         attr2set: default_distribution_format_version
      resources{0}.language:
         action: attribute_not_null
         attr2set: transfer_option_description_language
      projectionList{0}.projection_system:
         action: attribute_not_null
         attr2set: default_reference_system
      projectionList{0}.projection_system_version:
         action: attribute_not_null
         attr2set: default_reference_system_version
    -> ATTRIBUTE_MANAGER_NG_5
ATTRIBUTE_MANAGER_NG_5
    IN_YAML_TEXT:
      contacts{}.p-t_entity:
         action: attribute_not_null
         attr2set: p-t_entity
      contacts{}.p-t_entity_fr:
         action: attribute_not_null
         attr2set: p-t_entity_fr
      distributionList{}.format_version:
         action: attribute_not_null
         attr2set: default_distribution_format_version
      resources{}.language:
         action: attribute_not_null
         attr2set: transfer_option_description_language
      projectionList{}.projection_system:
         action: attribute_not_null
         attr2set: default_reference_system
      projectionList{}.projection_system_version:
         action: attribute_not_null
         attr2set: default_reference_system_version
    -> AttributeExposer_20

Bookmark: Language Translation
Note: Translates specific items from English to French
AWS_TRANSLATE
    ACTIVATE_TRANSLATION = $(ACTIVATE_TRANSLATION)
    ATTR_2_TRANSLATE = notes,title
    ATTR_LIST_2_TRANSLATE = tags{}.display_name,resources{}.name
    MODE = English-->French
    -> XML_PUBLISHER_NG
    TRANSLATION_PROBLEM -> AttributeExposer_12
AttributeExposer_12
    ATTR_TABLE = id,,title,
    -> TRANSLATION_PROBLEMS_GEO (writer XLSXW_1)
TRANSLATION_PROBLEMS_GEO (writer XLSXW_1)
    attributes: id string(200), title string(200)

Bookmark: XML CREATION AND WRITING
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
Note: CSV config file to map BC attributes to those required by the XML templates
XML_PUBLISHER_NG
    FEATURE_TYPE = Config_BC
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_OUT_WORKING_DIR)\XML_TEMPLATES\GMD_CITEDRESPONSIBLEPARTY.xml
    TEMPLATE_GMD_CONTACT = $(IN_OUT_WORKING_DIR)\XML_TEMPLATES\GMD_CONTACT.xml
    TEMPLATE_GMD_DISTRIBUTIONFORMAT = $(IN_OUT_WORKING_DIR)\XML_TEMPLATES\GMD_DISTRIBUTIONFORMAT.xml
    TEMPLATE_GMD_DISTRIBUTOR = $(IN_OUT_WORKING_DIR)\XML_TEMPLATES\GMD_DISTRIBUTOR.xml
    TEMPLATE_GMD_KEYWORDS = $(IN_OUT_WORKING_DIR)\XML_TEMPLATES\GMD_KEYWORDS.xml
    TEMPLATE_GMD_MDMETADATA = $(IN_OUT_WORKING_DIR)\XML_TEMPLATES\GMD_MDMETADATA.xml
    TEMPLATE_GMD_REFERENCESYSTEMINFO = $(IN_OUT_WORKING_DIR)\XML_TEMPLATES\GMD_REFERENCESYSTEMINFO.xml
    TEMPLATE_GMD_RESOURCEMAINTENANCE = $(IN_OUT_WORKING_DIR)\XML_TEMPLATES\GMD_RESOURCEMAINTENANCE.xml
    TEMPLATE_GMD_TOPICCATEGORY = $(IN_OUT_WORKING_DIR)\XML_TEMPLATES\GMD_TOPICCATEGORY.xml
    TEMPLATE_GMD_TRANSFEROPTIONS = $(IN_OUT_WORKING_DIR)\XML_TEMPLATES\GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> INVALID_METADATA (writer XLSXW_1)
    UPDATE_FAILED -> text_line (writer TEXTLINE_2)

Bookmark: Activate None Geo and Sample or fulle content
Note: NONE GEO activated?
Tester_4
    BOOL_OP = OR
    TEST_CLAUSE = TEST @UpperCase($(ACTIVATE_NON_GEO)) = YES
    TEST_MODE = TEST
    PASSED -> TestFilter_2
TestFilter_2
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_2
    SAMPLES FEATURES -> Sampler_4
Sampler_4
    MODE = ORIGINAL
    RATE = $(SAMPLE_SIZE)
    SAMPLE_TYPE_MULTIPLIER = -1
    SAMPLE_MODE = No
    SAMPLE_TYPE_LONG = First N Features
    SAMPLED -> Junction_2

Bookmark: Non-Geospatial Export
Note: Map update_frequency to CKAN
METADATA_VALUE_MAPPER_NG_4
    ATT_TO_MAP = update_cycle
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> METADATA_FORMAT_MAPPER_NG_4 [DATA_INPUT]
Note: Map resources{}.format to CKAN
METADATA_FORMAT_MAPPER_NG_4
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_NoneGeo (writer XLSXW_1)
    -> AttributeExposer
Note: Extract errors created by the METADATA_VALUE_MAPPER_NG
METADATA_VALUE_MAPPER_ERROR_MANAGER_2
    ERROR_OUTPUT -> ATTRIBUTE_MAPPING_ERRORS_NONE_GEO (writer XLSXW_1)
    DATA_OUTPUT -> AttributeExposer_17
ATTRIBUTE_MAPPING_ERRORS_NONE_GEO (writer XLSXW_1)
    attributes: error string(200), id string(200), _element_index number(20)
UNKNOWN_MIME_TYPE_NoneGeo (writer XLSXW_1)
    attributes: _unknown_mime_type string(8), _url_validation string(8), id string(8)

Bookmark: Generating TBS_SUBJECTbased on topic
AttributeExposer
    ATTR_TABLE = topic{}.value,
    -> ListCopier_3
ListCopier_3
    DEST_LIST = subject
    SRC_LIST = topic{}
    -> METADATA_VALUE_MAPPER_NG_9 [DATA_INPUT]
Note: Map TBS_Subject{}.value to CKAN
METADATA_VALUE_MAPPER_NG_9
    ATT_TO_MAP = subject{}.value
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUP_TABLES_DIR)
    P-T_ABBR = $(P-T_ABBR)
    -> AttributeExposer_14

Bookmark: Remove duplicate subject
AttributeExposer_14
    ATTR_TABLE = subject{}.value,
    -> ListDuplicateRemover
ListDuplicateRemover
    SRC_LIST = subject{}.value
    -> METADATA_VALUE_MAPPER_NG_6 [DATA_INPUT]

Bookmark: Generating Tbs Topic based on tags
Note: Map topic to tbs
METADATA_VALUE_MAPPER_NG_6
    ATT_TO_MAP = topic{}.value
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUP_TABLES_DIR)
    P-T_ABBR = $(P-T_ABBR)
    -> AttributeExposer_15

Bookmark: Remove duplicate topic
AttributeExposer_15
    ATTR_TABLE = topic{}.value,
    -> ListDuplicateRemover_2
ListDuplicateRemover_2
    SRC_LIST = topic{}.value
    -> METADATA_VALUE_MAPPER_ERROR_MANAGER_2

Bookmark: New Bookmark
AttributeExposer_17
    ATTR_TABLE = record_last_modified,,id,
    -> METADATA_DELTA_FINDER_GEN_2
METADATA_DELTA_FINDER_GEN_2
    ATTR_DATE_MODIFIED = record_last_modified
    LOCAL_SOURCE = Yes
    METADATA_OVERWRITE = $(METADATA_OVERWRITE)
    METADATA_TYPE = JSON-CKANExtCa
    SOURCE_DIRECTORY = $(OUT_JSON_LOCAL_DIR)
    VALIDATE_INSERT_PCT = $(VALIDATE_INSERT_PCT_JSON)
    YAML_FILE = $(IN_CSV_LOOKUP_TABLES_DIR)\$(P-T_ABBR)\metadata_delta_finder_$(P-T_ABBR)_non_geo.yaml
    Statistics -> StatisticsCalculator_Summary_3
    Update -> Junction_4
    Insert -> Junction_4
    Delete -> AttributeExposer_7
StatisticsCalculator_Summary_3: Logger
    LOG_FEATURE = NONE
    MAXFEATS = 20
    MESSAGE:
      ************************
      **** None Geo Unchanged Report ****
      ************************

      @Value(_real_count) features were unchanged

      ************************
      ************************
      ************************
    SEVERITY = INFO
AttributeExposer_7
    ATTR_TABLE = id,,title,
    -> DELETE_RECORDS_NONE_GEO (writer XLSXW_1)
DELETE_RECORDS_NONE_GEO (writer XLSXW_1)
    attributes: id string(200), title string(200)
Junction_4
    -> AWS_TRANSLATE_3

Bookmark: Language translation
Note: Translate some attributes using AWS translate
AWS_TRANSLATE_3
    ACTIVATE_TRANSLATION = $(ACTIVATE_TRANSLATION)
    ATTR_2_TRANSLATE = notes,title
    ATTR_LIST_2_TRANSLATE = tags{}.display_name,resources{}.name
    MODE = English-->French
    -> JSON_PUBLISHER_NG
    TRANSLATION_PROBLEM -> AttributeExposer_9
AttributeExposer_9
    ATTR_TABLE = id,,title,
    -> TRANSLATION_PROBLEM_NONE_GEO (writer XLSXW_1)
TRANSLATION_PROBLEM_NONE_GEO (writer XLSXW_1)
    attributes: id string(200), title string(200)
