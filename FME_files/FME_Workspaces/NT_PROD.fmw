FME workspace NT_PROD.fmw
Title: NT_PROD
Description: Description 
This workbench read and trasform all the metadata for the Northwest Territory (NT)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
SAMPLE_SIZE: Number of features to process. Zero (0) means process all the features. A number n greater than 0 means sample or process only the first n features.
URL_VALIDATION : Indicates to validate or not created URL. (Should be Yes for prod)
VALIDATE_INSERT_PCT :Indicates to valide insert percentage. 75 % or less insert/update record  (Should be Yes for prod)

Parameters:
- ACTIVATE_GEO = Yes
- ACTIVATE_NON_GEO = Yes
- ACTIVATE_TRANSLATION = Yes
- CATALOGUE_READER_SELECT = Yes
- IN_FFS_TESTING_FILE =
- FORCED_PYCSW_URL =
- LOCAL_SOURCE_METADATA_DELTA_FINDER = No
- LOCAL_WRITER = No
- METADATA_OVERWRITE = NO   # METADATA OVERWRITE
- IN_OUT_WORKING_DIR = $(FME_SHAREDRESOURCE_DATA)\PT_Harvester
- SAMPLE_SIZE = 0
- URL_VALIDATION = Yes
- VALIDATE_INSERT_PCT_JSON = Yes
- VALIDATE_INSERT_PCT_XML = Yes
- IN_CSV_LOOKUPTABLES_DIR = $(IN_OUT_WORKING_DIR)\LOOKUP_TABLES   # Lookup Tables Directory
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- IN_CSV_LOOKUP_TABLES_DIR = $(IN_OUT_WORKING_DIR)\LOOKUP_TABLES
- FME_SHAREDRESOURCE_DATA = C:\Data   # FME Flow Data Directory

Writers:
- XLSXW_1: XLSXW to $(IN_OUT_WORKING_DIR)
- TEXTLINE_1: TEXTLINE to $(OUT_XML_PASSED_DIR)
- TEXTLINE_2: TEXTLINE to $(OUT_XML_FAILED_DIR)
- TEXTLINE_3: TEXTLINE to $(OUT_XML_LOCAL_DIR)
- TEXTLINE_4: TEXTLINE to $(OUT_JSON_LOCAL_DIR)

Bookmark: metadata_reader
Creator_2
    GEOMTYPE = Geometry Object
    NUM = 1
    CREATED -> Tester
Tester
    BOOL_OP = OR
    TEST_CLAUSE = TEST $(CATALOGUE_READER_SELECT) = Yes
    TEST_MODE = TEST
    PASSED -> NT_CATALOGUE_READER
    FAILED -> FeatureReader [INITIATOR]
NT_CATALOGUE_READER
    DATA_METADATA = Yes
    DOCUMENTS_METADATA = Yes
    MAPS_METADATA = Yes
    MAP_VIEWERS_METADATA = Yes
    REPORTS_METADATA = Yes
    WMS_METADATA = Yes
    DATA -> Junction_4
    MAPS -> Junction_4
    WMS -> Junction_4
    REPORTS -> Junction_4
    DOCUMENTS -> Junction_4
    MAP_VIEWERS -> Junction_4
Junction_4
    -> AttributeExposer
FeatureReader
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> AttributeExposer

Bookmark: Rename and filter duplicate attributes
AttributeExposer
    ATTR_TABLE = description,,title,,resource_type,,resource_category,,data_category,,publication_date,,resources{0}.url,,resources{}.url,,resources{}.name,,resources{}.format,
    -> AttributeManager_4
NT_metadata_merger
    -> Junction_2
Junction_2
    -> UNIQUE_ID_CREATOR
Note: Unique uuid created from metadata title
UNIQUE_ID_CREATOR
    UNIQUE_ATT = @Value(title)
    -> ATTRIBUTE_UNEXPOSER_2
ATTRIBUTE_UNEXPOSER_2
    -> NT_resources_merger
NT_resources_merger
    IN_CSV_LOOKUPTABLES_DIR = $(IN_CSV_LOOKUP_TABLES_DIR)
    P-T_ABBR = $(P-T_ABBR)
    feature_type = NT_metadata_merger
    feature_type_title = NT_metadata_merger_title
    Legend_or_UserGuide_in_title -> AttributeExposer_16
    -> PythonCaller
AttributeExposer_16
    ATTR_TABLE = format,
    -> NT_METADATA_MERGER (writer XLSXW_1)
NT_METADATA_MERGER (writer XLSXW_1)
    attributes: erreur_NT_resources_merger string(200), id string(200), format string(200)

Bookmark: Rename attributes
AttributeManager_4
    ATTR_TABLE:
      REMOVE _creation_instance (uint64)
      REMOVE _html_code (buffer)
      REMOVE _url_error (buffer)
      REMOVE _html_detail (buffer)
      RENAME_SET_VALUE description > notes (varchar(200))
      RENAME_SET_VALUE publication_date > record_publish_date (varchar(200)) = FME_CONDITIONAL:DEFAULT_VALUE'_FME_NO_OP_'BOOL_OP;OR;COMPOSITE_TEST;1;CASE_INSENSITIVE_TEST @Value(record_publish_date) CONTAINS November 2011'2011-11-01'FME_NUM_CONDITIONS2___
      RENAME_SET_VALUE data_category > iso_topic{0}.topic_value (varchar(200))
    -> AttributeCopier
AttributeCopier
    ATTR_TABLE:
      COPY record_publish_date > record_create_date
      COPY record_publish_date > record_last_modified
    MISSING_INPUT_ATTRS = PRESERVE
    -> TestFilter

Bookmark: merge Mackenzie Valley Air Photo data and exclude Oziexplorer and CanMatrix metadata
TestFilter
    DEFAULT_VALUE = <UNFILTERED>
    PASSED_TEST_GROUP_OUTPUT = FIRST
    TEST_LIST:
      "BOOL_OP,OR,COMPOSITE_TEST,""""""1"""""",TEST_CLAUSE,CASE_INSENSITIVE_TEST @Value(notes) CONTAINS Mackenzie Valley Air Photo Digital Orthotiles",Mackenzie Valley Orthotiles,"BOOL_OP,OR,COMPOSITE_TEST,""""""1"""""",TEST_CLAUSE,CASE_INSENSITIVE_TEST @Value(notes) CONTAINS Mackenzie Valley Air Photo Contours Data",Mackenzie Valley Contours Data,"BOOL_OP,OR,COMPOSITE_TEST,""""""1"""""",TEST_CLAUSE,CASE_INSENSITIVE_TEST @Value(notes) CONTAINS Mackenzie Valley Air Photo Digital Elevation Model Data",Mackenzie Valley DEM,"BOOL_OP,OR,COMPOSITE_TEST,""""""1 OR 2"""""",TEST_CLAUSE,CASE_INSENSITIVE_TEST @Value(resource_category) CONTAINS Oziexplorer
      CASE_INSENSITIVE_TEST @Value(title) CONTAINS CanMatrix",Oziexplorer_CanMatrix,"BOOL_OP,OR,COMPOSITE_TEST,""""""1 OR 2"""""",TEST_CLAUSE,CASE_INSENSITIVE_TEST @Value(title) CONTAINS Government of Canada
      CASE_INSENSITIVE_TEST @Value(title) CONTAINS CCOG",Government of Canada dataset
    Mackenzie Valley Orthotiles -> AttributeManager_5
    Mackenzie Valley Contours Data -> AttributeManager_6
    Mackenzie Valley DEM -> AttributeManager_7
    <UNFILTERED> -> NT_metadata_merger
AttributeManager_5
    ATTR_TABLE:
      RENAME_SET_VALUE notes > title (varchar(200))
      SET_TO resources{0}.url (varchar(200)) = https://www.geomatics.gov.nt.ca/Downloads/Raster/MVAP%20Orthotiles/
      SET_TO resources{0}.name (varchar(200)) = Mackenzie Valley Air Photo Digital Orthotiles
      SET_TO resources{0}.format (varchar(200)) = ftp
    -> DuplicateFilter_2
AttributeManager_6
    ATTR_TABLE:
      RENAME_SET_VALUE notes > title (varchar(200))
      SET_TO resources{0}.url (varchar(200)) = https://www.geomatics.gov.nt.ca/Downloads/Vector/MVAP%20Contours/
      SET_TO resources{0}.name (varchar(200)) = Mackenzie Valley Air Photo Contours Data
      SET_TO resources{0}.format (varchar(200)) = ftp
    -> DuplicateFilter_2
AttributeManager_7
    ATTR_TABLE:
      RENAME_SET_VALUE notes > title (varchar(200))
      SET_TO resources{0}.url (varchar(200)) = https://www.geomatics.gov.nt.ca/Downloads/Raster/MVAP%20DEM/
      SET_TO resources{0}.name (varchar(200)) = Mackenzie Valley Air Photo Digital Elevation Model Data
      SET_TO resources{0}.format (varchar(200)) = ftp
    -> DuplicateFilter_2
DuplicateFilter_2
    INPUT_ORDERED_CHOICE_LOOKUP = NO
    KEYATTR = title
    INPUT_ORDERED_CHOICE = No
    UNIQUE -> Junction_2

Bookmark: Date conversion
Note: extract 'CreaDate' from ESRI REST
PythonCaller
    PYTHONSOURCE:
      import fme
      import fmeobjects
      import requests
      import json
      import xmltodict
      from Python.FME_utils import FME_utils

      def FeatureProcessor(feature):

          max_index=FME_utils.max_index_attribute_list(feature,'resources{}.url')
          for j in range(max_index+1):
              url = feature.getAttribute('resources{%i}.url'%(j))
              if url.endswith('/MapServer'):
                x = url+'/info/metadata'

                try:
                 r = requests.get(x,allow_redirects=False,timeout=90,verify=False)
                 decoded_response = r.content.decode("utf-8")
                 response_json = json.loads(json.dumps(xmltodict.parse(decoded_response)))
                 publish_date=response_json['metadata']['Esri']['CreaDate']
                 feature.setAttribute('REST_publish_date',publish_date)
                except:
                 pass
    PYTHONSYMBOL = FeatureProcessor
    -> AttributeExposer_4
AttributeExposer_4
    ATTR_TABLE = record_create_date,,record_publish_date,,record_last_modified,,REST_publish_date,
    -> DateTimeConverter_2
DateTimeConverter_2
    DATETIME_ATTR = record_create_date record_last_modified record_publish_date REST_publish_date
    OUT_FORMAT = %Y-%m-%d
    PASSTHROUGH = NO
    REPAIR_INPUT = YES
    -> Junction_5
    <REJECTED> -> AttributeRemover_2
AttributeRemover_2
    REMOVE_ATTRS = fme_rejection_code
    -> Junction_5
Junction_5
    -> ATTRIBUTE_UNEXPOSER
ATTRIBUTE_UNEXPOSER
    -> ATTRIBUTE_VALUE_TEXT_CLEANER

Bookmark: Attributes manager
ATTRIBUTE_VALUE_TEXT_CLEANER
    -> DEFAULT_ATTRIBUTE_MAPPER_NG
DEFAULT_ATTRIBUTE_MAPPER_NG
    FEATURE_TYPE = Default_NT
    IN_CSV_LOOKUP_TABLES_DIR = $(IN_CSV_LOOKUPTABLES_DIR)
    P-T_ABBR = $(P-T_ABBR)
    -> ATTRIBUTE_MANAGER_NG
ATTRIBUTE_MANAGER_NG
    IN_YAML_TEXT:
      record_last_modified:
          action: attribute_not_null
          attr2set: REST_publish_date

      record_publish_date:
          action: attribute_not_null
          attr2set: REST_publish_date

      record_create_date:
          action: attribute_not_null
          attr2set: REST_publish_date
    -> ATTRIBUTE_MANAGER_NG_2
ATTRIBUTE_MANAGER_NG_2
    IN_YAML_TEXT:
      iso_topic{0}.topic_value:
          action: attribute_not_null
          attr2set: default_topic


      record_last_modified:
          action: attribute_not_null
          attr2set: default_record_date

      record_publish_date:
          action: attribute_not_null
          attr2set: default_record_date

      record_create_date:
          action: attribute_not_null
          attr2set: default_record_date

      notes:
          action: attribute_not_null
          attr2set: title
    -> PythonCaller_3

Bookmark: Format and resources manager and validator
Note: If resource{}.url response.headers ('location') ends with: / .zip: format = ZIP / .pdf: format = PDF / for formats: other and pdf
PythonCaller_3
    PYTHONSOURCE:
      import fme
      import fmeobjects
      import requests
      from Python.FME_utils import FME_utils

      #def processFeature(feature):
      #    pass

      # Template Class Interface:
      # When using this class, make sure its name is set as the value of
      # the 'Class or Function to Process Features' transformer parameter
      def FeatureProcessor(feature):

          max_index=FME_utils.max_index_attribute_list(feature,'resources{}.url')
          for j in range(max_index+1):
              x = feature.getAttribute('resources{%i}.url'%(j))
              format = feature.getAttribute('resources{%i}.format'%(j))
              if ('OTHER') in format.upper() or ('PDF') in format.upper():
                  response = requests.head(x,allow_redirects=False,timeout=90,verify=False)
                  headers = response.headers
                  location = headers.get("location")
                  if location is not None:
                      if location.lower().endswith('.zip'):
                         feature.setAttribute('resources{%i}.format'%(j),'ZIP')
                      elif location.lower().endswith('.pdf'):
                         feature.setAttribute('resources{%i}.format'%(j),'PDF')
                      else:
                         feature.setAttributeNullWithType('resources{%i}.format'%(j),fmeobjects.FME_ATTR_ENCODED_STRING)
                  else:
                     feature.setAttributeNullWithType('resources{%i}.format'%(j),fmeobjects.FME_ATTR_ENCODED_STRING)
    PYTHONSYMBOL = FeatureProcessor
    -> PythonCaller_2
Note: If resource{}.url contains WMSServer?; add request=GetCapabilities&service=WMS at the end or the url
PythonCaller_2
    PYTHONSOURCE:
      import fme
      import fmeobjects
      from Python.FME_utils import FME_utils

      #def processFeature(feature):
      #    pass

      # Template Class Interface:
      # When using this class, make sure its name is set as the value of
      # the 'Class or Function to Process Features' transformer parameter
      def FeatureProcessor(feature):
          i=0

          max_index=FME_utils.max_index_attribute_list(feature,'resources{}.url')
          for j in range(max_index+1):
              x = feature.getAttribute('resources{%i}.url'%(j))
              if x:
               if x.endswith('WMSServer?'):
                feature.setAttribute('resources{%i}.url'%(j),x+'request=GetCapabilities&service=WMS')
              i=i+1
    PYTHONSYMBOL = FeatureProcessor
    -> PythonCaller_4
Note: If format is EsriRest or other; remove format value so that it is added in empty format mapper ng; to ensure that only valid EsriRest format are added
PythonCaller_4
    PYTHONSOURCE:
      import fme
      import fmeobjects
      from Python.FME_utils import FME_utils

      #def processFeature(feature):
      #    pass

      # Template Class Interface:
      # When using this class, make sure its name is set as the value of
      # the 'Class or Function to Process Features' transformer parameter
      def FeatureProcessor(feature):
          i=0

          max_index=FME_utils.max_index_attribute_list(feature,'resources{}.format')
          for j in range(max_index+1):
              x = feature.getAttribute('resources{%i}.format'%(j))
              if x:
               if ('REST') in x.upper() or ('OTHER') in x.upper():
                feature.setAttributeNullWithType('resources{%i}.format'%(j),fmeobjects.FME_ATTR_ENCODED_STRING)
              i=i+1
    PYTHONSYMBOL = FeatureProcessor
    -> EMPTY_FORMAT_MAPPER_NG [DATA_INPUT]
EMPTY_FORMAT_MAPPER_NG
    CSV_FORMAT = Format
    CSV_MIME_TYPE = Mime_type
    IN_CSV_LOOKUP_TABLES_DIR = $(IN_CSV_LOOKUPTABLES_DIR)
    P-T_ABBR = $(P-T_ABBR)
    URL_VALIDATION = $(URL_VALIDATION)
    DATA_OUTPUT -> FORMAT_VALIDATOR
    UNKNOWN_MIME_TYPE -> UNKNOWN_MIME_TYPE (writer XLSXW_1)
FORMAT_VALIDATOR
    -> PythonCaller_5
RESOURCES_VALIDATOR
    -> URL_HTTPS_MAKER [UUIDGenerator_Input]
URL_HTTPS_MAKER
    P-T_ABBR = $(P-T_ABBR)
    URL_VALIDATION = $(URL_VALIDATION)
    -> GEO_NONE_GEO_SELECTOR
Note: Possible values for NT_resources_language: / english; french; english_and_french
UNKNOWN_RESOURCE_LANGUAGE (writer XLSXW_1)
    attributes: url auto(20), id auto(20)
UNKNOWN_MIME_TYPE (writer XLSXW_1)
    attributes: _order string(200), _url_validation string(200), _unknown_mime_type string(200), id string(200)

Bookmark: language resources manager
Note: add resources{}.language and put defaut value to: english
PythonCaller_5
    PYTHONSOURCE:
      import fme
      import fmeobjects
      from Python.FME_utils import FME_utils

      # Template Function interface:
      # When using this function, make sure its name is set as the value of
      # the 'Class or Function to Process Features' transformer parameter
      def FeatureProcessor(feature):
          i=0

          max_index=FME_utils.max_index_attribute_list(feature,'resources{}')
          for j in range(max_index+1):
              feature.setAttribute('resources{%i}.language'%(j),"english")
              i=i+1
    PYTHONSYMBOL = FeatureProcessor
    -> NT_language_manager
Note: change resources{}.language value base on a look-up table (NT_resources_language)
NT_language_manager
    IN_CSV_LOOKUP_TABLES_DIR = $(IN_CSV_LOOKUP_TABLES_DIR)
    P-T_ABBR = $(P-T_ABBR)
    feature_type = NT_resources_language
    res_url_unknown_language -> UNKNOWN_RESOURCE_LANGUAGE (writer XLSXW_1)
    -> RESOURCES_VALIDATOR

Bookmark: Geo non-geo selector
GEO_NONE_GEO_SELECTOR
    CSV_FILE_NAME = GeoSpatialValidation
    CSV_PATH = $(IN_CSV_LOOKUPTABLES_DIR)
    CSV_PROVINCE = $(P-T_ABBR)
    YAML_DIRECTIVES:
      resources{}.format:
        domain: lookup_table_format
        spatial_type: overwrite
        not_found: log
        search_type: equals
    GEOSPATIAL -> SPATIAL_TYPE_MAPPER_NG [DATA_INPUT]
    NONE_GEOSPATIAL -> MANUAL_GEOSPATIAL_SETTER_NG [DATA_INPUT]
    LOG_ERROR -> GEOSPATIAL_FORMAT_NOT_MAPPED (writer XLSXW_1)
SPATIAL_TYPE_MAPPER_NG
    FEATURE_TYPE = SpatialType_$(P-T_ABBR)
    IN_CSV_LOOKUP_TABLES_DIR = $(IN_CSV_LOOKUPTABLES_DIR)
    P-T_ABBR = $(P-T_ABBR)
    DATA_OUTPUT_FAILED -> AttributeExposer_5
    DATA_OUTPUT_PASSED -> TestFilter_2
AttributeExposer_5
    ATTR_TABLE = id,,title,,notes,
    -> SPATIA_TYPE_NOT_MAPPED (writer XLSXW_1)
SPATIA_TYPE_NOT_MAPPED (writer XLSXW_1)
    attributes: id string(200), title string(200), notes string(200)
MANUAL_GEOSPATIAL_SETTER_NG
    FEATURE_TYPE = UnmappedGeoData_$(P-T_ABBR)
    IN_CSV_LOOKUP_TABLES_DIR = $(IN_CSV_LOOKUPTABLES_DIR)
    P-T_ABBR = $(P-T_ABBR)
    GEOSPATIAL -> TestFilter_2
    NON-GEOSPATIAL -> TestFilter_4
    UNMAPPED_DATA -> UNMAPPED_DATA (writer XLSXW_1)
TestFilter_2
    DEFAULT_VALUE = <UNFILTERED>
    PASSED_TEST_GROUP_OUTPUT = FIRST
    TEST_LIST = "BOOL_OP,OR,COMPOSITE_TEST,""""""1"""""",TEST_CLAUSE,CASE_INSENSITIVE_TEST $(ACTIVATE_GEO) = yes",GEO_ACTIVATE
    GEO_ACTIVATE -> TestFilter_5
UNMAPPED_DATA (writer XLSXW_1)
    attributes: id string(200), notes string(200), title string(200), url string(200)
TestFilter_4
    DEFAULT_VALUE = <UNFILTERED>
    PASSED_TEST_GROUP_OUTPUT = FIRST
    TEST_LIST = "BOOL_OP,OR,COMPOSITE_TEST,""""""1"""""",TEST_CLAUSE,CASE_INSENSITIVE_TEST $(ACTIVATE_NON_GEO) = yes",ACTIVATE_NON_GEO
    ACTIVATE_NON_GEO -> TestFilter_3
GEOSPATIAL_FORMAT_NOT_MAPPED (writer XLSXW_1)
    attributes: id string(200), format string(200)

Bookmark: Samples or full content
TestFilter_5
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_8
    SAMPLES FEATURES -> Sampler_2
Sampler_2
    MODE = ORIGINAL
    RATE = $(SAMPLE_SIZE)
    SAMPLE_TYPE_MULTIPLIER = -1
    SAMPLE_MODE = No
    SAMPLE_TYPE_LONG = First N Features
    SAMPLED -> Junction_8

Bookmark: Geo metadata processing
Junction_8
    -> METADATA_VALUE_MAPPER_NG_2 [DATA_INPUT]
AttributeCreator_3
    ATTR_TABLE = SET_TO csw_url (varchar(200)) = $(FORCED_PYCSW_URL)
    -> ATTRIBUTE_MANAGER_NG_4
AttributeExposer_20
    ATTR_TABLE = search_criteria_pycsw,,csw_url,,record_last_modified,,id,
    -> METADATA_DELTA_FINDER_GEN
METADATA_DELTA_FINDER_GEN
    ATTR_DATE_MODIFIED = record_last_modified
    CSW_FILTER = @Value(search_criteria_pycsw)
    LOCAL_SOURCE = $(LOCAL_SOURCE_METADATA_DELTA_FINDER)
    METADATA_OVERWRITE = $(METADATA_OVERWRITE)
    METADATA_TYPE = XML-HNAP
    SOURCE_DIRECTORY = $(OUT_XML_LOCAL_DIR)
    SOURCE_URL = @Value(csw_url)
    VALIDATE_INSERT_PCT = $(VALIDATE_INSERT_PCT_XML)
    YAML_FILE = $(IN_CSV_LOOKUP_TABLES_DIR)\$(P-T_ABBR)\metadata_delta_finder_$(P-T_ABBR)_geo.yaml
    Statistics -> StatisticsCalculator_Summary_2
    Update -> Junction
    Insert -> Junction
    Delete -> AttributeExposer_6
Note: Log statistics
StatisticsCalculator_Summary_2: Logger
    LOG_FEATURE = NONE
    MAXFEATS = 20
    MESSAGE:
      ************************
      **** Geo Features: Unchanged Report ****
      ************************

      @Value(_real_count) features were unchanged

      ************************
      ************************
      ************************
    SEVERITY = INFO
Junction
    -> AWS_TRANSLATE_2
AttributeExposer_6
    ATTR_TABLE = id,,title,,_timestamp,
    -> DELETED_RECORDS_GEO (writer XLSXW_1)
DELETED_RECORDS_GEO (writer XLSXW_1)
    attributes: id string(200), title string(200), _timestamp string(200)

Bookmark: Metadata Value Mapping - GEO
Note: Topic (categfory)
METADATA_VALUE_MAPPER_NG_2
    ATT_TO_MAP = iso_topic{}.topic_value
    CODE_REFRESH = NO
    ENGLISH_REFRESH = YES
    ERROR_NOT_MAPPED = YES
    FEATURE_TYPE = Topic
    FRENCH_REFRESH = NO
    IN_CSV_LOOKUP_TABLES_DIR = $(IN_CSV_LOOKUPTABLES_DIR)
    P-T_ABBR = $(P-T_ABBR)
    -> METADATA_VALUE_MAPPER_NG_14 [DATA_INPUT]
Note: resources{}.language
METADATA_VALUE_MAPPER_NG_14
    ATT_TO_MAP = resources{}.language
    CODE_REFRESH = NO
    ENGLISH_REFRESH = YES
    ERROR_NOT_MAPPED = YES
    FEATURE_TYPE = TransferLang_NT
    FRENCH_REFRESH = NO
    IN_CSV_LOOKUP_TABLES_DIR = $(IN_CSV_LOOKUP_TABLES_DIR)
    P-T_ABBR = $(P-T_ABBR)
    -> METADATA_VALUE_MAPPER_NG_3 [DATA_INPUT]
Note: Role
METADATA_VALUE_MAPPER_NG_3
    ATT_TO_MAP = role
    CODE_REFRESH = YES
    ENGLISH_REFRESH = YES
    ERROR_NOT_MAPPED = YES
    FEATURE_TYPE = Role
    FRENCH_REFRESH = YES
    IN_CSV_LOOKUP_TABLES_DIR = $(IN_CSV_LOOKUPTABLES_DIR)
    P-T_ABBR = $(P-T_ABBR)
    -> METADATA_VALUE_MAPPER_NG_4 [DATA_INPUT]
Note: Update
METADATA_VALUE_MAPPER_NG_4
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUPTABLES_DIR)
    P-T_ABBR = $(P-T_ABBR)
    -> METADATA_VALUE_MAPPER_NG_5 [DATA_INPUT]
Note: Progress
METADATA_VALUE_MAPPER_NG_5
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUPTABLES_DIR)
    P-T_ABBR = $(P-T_ABBR)
    -> METADATA_VALUE_MAPPER_NG_7 [DATA_INPUT]
Note: SpatialRepresentation
METADATA_VALUE_MAPPER_NG_7
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUPTABLES_DIR)
    P-T_ABBR = $(P-T_ABBR)
    -> METADATA_FORMAT_MAPPER_NG [DATA_INPUT]
Note: Format
METADATA_FORMAT_MAPPER_NG
    ATT_TO_MAP = resources{}.format
    ERROR_NOT_MAPPED = YES
    FEATURE_TYPE = Format
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_Geo (writer XLSXW_1)
    -> METADATA_VALUE_MAPPER_ERROR_MANAGER
UNKNOWN_MIME_TYPE_Geo (writer XLSXW_1)
    attributes: _unknown_mime_type string(8), _url_validation string(8), id string(8)
METADATA_VALUE_MAPPER_ERROR_MANAGER
    ERROR_OUTPUT -> METADATA_MAPPING_ERRORS_GEO (writer XLSXW_1)
    DATA_OUTPUT -> RESOURCE_NAME_UNDERSCORE_REMOVER
METADATA_MAPPING_ERRORS_GEO (writer XLSXW_1)
    attributes: error string(200), id string(200)

Bookmark: Remove all underscores from resources{}.name attributes
RESOURCE_NAME_UNDERSCORE_REMOVER
    DATA_OUTPUT -> PythonCaller_8

Bookmark: Remove ESRI REST NT webmap wiever resources
Note: Remove resources{} that contains 'www.arcgis.com/home/webmap/viewer' in their url / The resources_validator CT is used to reset indexes in the resources list.
PythonCaller_8
    PYTHONSOURCE:
      import fme
      import fmeobjects
      from Python.FME_utils import FME_utils

      def FeatureProcessor(feature):

          max_index=FME_utils.max_index_attribute_list(feature,'resources{}')
          for j in range(max_index+1):
              url = feature.getAttribute('resources{%i}.url'%(j))

              if 'www.arcgis.com/home/webmap/viewer' in url:
                 feature.removeAttrsWithPrefix('resources{%i}'%(j))
    PYTHONSYMBOL = FeatureProcessor
    -> RESOURCES_VALIDATOR_2
RESOURCES_VALIDATOR_2
    -> AttributeExposer_3

Bookmark: HNAP RULES
AttributeExposer_3
    ATTR_TABLE = id,
    -> Tester_2
Note: Do not add an ESRI REST protocol for NWT Simplified Basemap; it is not working in viewer
Tester_2
    BOOL_OP = OR
    TEST_CLAUSE = CASE_INSENSITIVE_TEST @Value(id) CONTAINS c87481e1-eb08-8b85-3724-c654f364b04f
    TEST_MODE = CASE_INSENSITIVE_TEST
    PASSED -> PythonCaller_6
    FAILED -> WMS_REST_LANGUAGE_FORMATTER
WMS_REST_LANGUAGE_FORMATTER
    -> AttributeExposer_2
PythonCaller_6
    PYTHONSOURCE:
      import fme
      import fmeobjects
      from Python.FME_utils import FME_utils

      def FeatureProcessor(feature):

          max_index=FME_utils.max_index_attribute_list(feature,'resources{}.format')
          for j in range(max_index+1):
              feature.setAttribute('resources{%i}.protocol'%(j),'HTTPS')
              feature.setAttributeNullWithType('resources{%i}.xlink_role'%(j),fmeobjects.FME_ATTR_ENCODED_STRING)
    PYTHONSYMBOL = FeatureProcessor
    -> Junction_3
Junction_3
    -> DUPLICATE_SERVICE_REMOVER
DUPLICATE_SERVICE_REMOVER
    -> GMD_SECTION_DATA_EXTRACTION
GMD_SECTION_DATA_EXTRACTION
    -> REMOVE_BROKEN_URL_WMS_ESRI_REST

Bookmark: If format contains an ESRI REST and WMS; add only resources{}.protocol + xlink_role to ESRI REST
AttributeExposer_2
    ATTR_TABLE = resources{}.format,
    -> ListSearcher
Note: If there is an ESRI REST resource
ListSearcher
    ATTR_VALUE = REST
    CASE = CASE_SENSITIVE
    INDEX_ATTR = _list_index
    LIST_ATTR = resources{}.format
    MATCHTYPE = REGULAR_EXPRESSION_ENCODED
    FOUND -> PythonCaller_7
    NOT_FOUND -> Junction_3
Note: If format = WMS and there is an ESRI REST format, change resources{}.protocol to 'HTTPS' and xlink_role to NULL to avoid showing ESRI REST and WMS in the viewer; and keep only one WMS feature. / The resources_validator CT is used to reset indexes in the resources list.
PythonCaller_7
    PYTHONSOURCE:
      import fme
      import fmeobjects
      from Python.FME_utils import FME_utils


      def FeatureProcessor(feature):
          dict_1 = {}

          max_index=FME_utils.max_index_attribute_list(feature,'resources{}')
          for j in range(max_index+1):
              format = feature.getAttribute('resources{%i}.format'%(j))
              url = feature.getAttribute('resources{%i}.url'%(j))

              if format == 'WMS':
                dict_1[url] = j
                feature.setAttribute('resources{%i}.protocol'%(j),'HTTPS')
                feature.setAttributeNullWithType('resources{%i}.xlink_role'%(j),fmeobjects.FME_ATTR_ENCODED_STRING)


          max_index=FME_utils.max_index_attribute_list(feature,'resources{}')
          for j in range(max_index+1):
              format = feature.getAttribute('resources{%i}.format'%(j))
              url = feature.getAttribute('resources{%i}.url'%(j))

              if format == 'WMS':
                 if j == dict_1[url]:
                    feature.removeAttrsWithPrefix('resources{%i}'%(j))
    PYTHONSYMBOL = FeatureProcessor
    -> RESOURCES_VALIDATOR_3
RESOURCES_VALIDATOR_3
    -> DUPLICATE_SERVICE_REMOVER

Bookmark: Drop Broken Web Services
REMOVE_BROKEN_URL_WMS_ESRI_REST
    URL_VALIDATION = Yes
    -> AttributeCreator_3
    FAULTY_URL_OUTPUT -> MAP_SERVICE_URL_ERROR (writer XLSXW_1)
MAP_SERVICE_URL_ERROR (writer XLSXW_1)
    attributes: id string(200), url string(200), format string(200), _url_failure_message string(20)

Bookmark: Listes Metadata_delta_finder
ATTRIBUTE_MANAGER_NG_4
    IN_YAML_TEXT:
      contacts{0}.role_code:
         action: attribute_not_null
         attr2set: role_code
      contacts{0}.role:
         action: attribute_not_null
         attr2set: role
      contacts{0}.role_fr:
         action: attribute_not_null
         attr2set: role_fr
      contacts{0}.p-t_entity:
         action: attribute_not_null
         attr2set: p-t_entity
      contacts{0}.p-t_entity_fr:
         action: attribute_not_null
         attr2set: p-t_entity_fr
      contacts{0}.sector:
         action: attribute_not_null
         attr2set: sector
      contacts{0}.sector_fr:
         action: attribute_not_null
         attr2set: sector_fr
      contacts{0}.email:
         action: attribute_not_null
         attr2set: contact_email
      distributionList{0}.format_version:
         action: attribute_not_null
         attr2set: distribution_format_version
      resources{0}.language:
         action: attribute_not_null
         attr2set: transfer_desc_locale_default
    -> ATTRIBUTE_MANAGER_NG_5
ATTRIBUTE_MANAGER_NG_5
    IN_YAML_TEXT:
      contacts{}.role_code:
         action: attribute_not_null
         attr2set: role_code
      contacts{}.role:
         action: attribute_not_null
         attr2set: role
      contacts{}.role_fr:
         action: attribute_not_null
         attr2set: role_fr
      contacts{}.p-t_entity:
         action: attribute_not_null
         attr2set: p-t_entity
      contacts{}.p-t_entity_fr:
         action: attribute_not_null
         attr2set: p-t_entity_fr
      contacts{}.sector:
         action: attribute_not_null
         attr2set: sector
      contacts{}.sector_fr:
         action: attribute_not_null
         attr2set: sector_fr
      contacts{}.email:
         action: attribute_not_null
         attr2set: contact_email
      distributionList{}.format_version:
         action: attribute_not_null
         attr2set: distribution_format_version
      resources{}.language:
         action: attribute_not_null
         attr2set: transfer_desc_locale_default
    -> AttributeExposer_20

Bookmark: AWS Translation
AWS_TRANSLATE_2
    ACTIVATE_TRANSLATION = $(ACTIVATE_TRANSLATION)
    ATTR_2_TRANSLATE = notes,title
    ATTR_LIST_2_TRANSLATE = resources{}.name
    MODE = English-->French
    -> XML_PUBLISHER_NG
    TRANSLATION_PROBLEM -> AttributeExposer_12
AttributeExposer_12
    ATTR_TABLE = id,,title,,_timestamp,
    -> TRANSLATION_PROBLEMS_GEO (writer XLSXW_1)
TRANSLATION_PROBLEMS_GEO (writer XLSXW_1)
    attributes: id string(200), title string(200), _timestamp string(200)

Bookmark: XML CREATION AND WRITING
XML_PUBLISHER_NG
    FEATURE_TYPE = Config_NT
    IN_CSV_LOOKUP_TABLES_DIR = $(IN_CSV_LOOKUPTABLES_DIR)
    LOCAL_WRITER = $(LOCAL_WRITER)
    P-T_ABBR = $(P-T_ABBR)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> INVALID_METADATA (writer XLSXW_1)
    UPDATE_FAILED -> text_line (writer TEXTLINE_2)
Note: Writes XML to a local folder without publishing to PyCSW, and without the PyCSW transaction headers and footers
text_line (writer TEXTLINE_3)
    attributes: text_line_data buffer
text_line (writer TEXTLINE_1)
    attributes: text_line_data buffer
text_line (writer TEXTLINE_2)
    attributes: text_line_data buffer
INVALID_METADATA (writer XLSXW_1)
    attributes: id auto(20)

Bookmark: Samples or full content
TestFilter_3
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_6
    SAMPLES FEATURES -> Sampler_3
Sampler_3
    MODE = ORIGINAL
    RATE = $(SAMPLE_SIZE)
    SAMPLE_TYPE_MULTIPLIER = -1
    SAMPLE_MODE = No
    SAMPLE_TYPE_LONG = First N Features
    SAMPLED -> Junction_6

Bookmark: Non-geo metadata processing
Junction_6
    -> METADATA_VALUE_MAPPER_NG_10 [DATA_INPUT]
Note: Adjusting update frequency value
METADATA_VALUE_MAPPER_NG_10
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUPTABLES_DIR)
    P-T_ABBR = $(P-T_ABBR)
    -> METADATA_FORMAT_MAPPER_NG_2 [DATA_INPUT]
Note: resources{}.format
METADATA_FORMAT_MAPPER_NG_2
    ATT_TO_MAP = resources{}.format
    ERROR_NOT_MAPPED = YES
    FEATURE_TYPE = Format_TBS
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_NoneGeo (writer XLSXW_1)
    -> METADATA_VALUE_MAPPER_NG_11 [DATA_INPUT]
UNKNOWN_MIME_TYPE_NoneGeo (writer XLSXW_1)
    attributes: _unknown_mime_type string(8), _url_validation string(8), id string(8)
Note: resources{}.language
METADATA_VALUE_MAPPER_NG_11
    ATT_TO_MAP = resources{}.language
    CODE_REFRESH = NO
    ENGLISH_REFRESH = YES
    ERROR_NOT_MAPPED = YES
    FEATURE_TYPE = TransferLang_NT_tbs
    FRENCH_REFRESH = NO
    IN_CSV_LOOKUP_TABLES_DIR = $(IN_CSV_LOOKUP_TABLES_DIR)
    P-T_ABBR = $(P-T_ABBR)
    -> AttributeExposer_7
Note: Creates list of errors found and not corrected in mapping
METADATA_VALUE_MAPPER_ERROR_MANAGER_2
    ERROR_OUTPUT -> METADATA_MAPPING_ERRORS_NON_GEO (writer XLSXW_1)
    DATA_OUTPUT -> AttributeExposer_13
AttributeExposer_13
    ATTR_TABLE = record_last_modified,,id,
    -> METADATA_DELTA_FINDER_GEN_2
Note: Translates specific items from English to French
AWS_TRANSLATE_3
    ACTIVATE_TRANSLATION = $(ACTIVATE_TRANSLATION)
    ATTR_2_TRANSLATE = notes,title
    ATTR_LIST_2_TRANSLATE = resources{}.name
    MODE = English-->French
    -> JSON_PUBLISHER_NG
    TRANSLATION_PROBLEM -> AttributeExposer_15
AttributeExposer_15
    ATTR_TABLE = id,,title,
    -> TRANSLATION_PROBLEMS_NON_GEO (writer XLSXW_1)
TRANSLATION_PROBLEMS_NON_GEO (writer XLSXW_1)
    attributes: id string(200), title string(200)
METADATA_MAPPING_ERRORS_NON_GEO (writer XLSXW_1)
    attributes: error string(200), id string(200)

Bookmark: TOPICS value mapper from iso_topic{}.topic_value list attributes
AttributeExposer_7
    ATTR_TABLE = iso_topic{}.topic_value,
    -> ListCopier_2
ListCopier_2
    DEST_LIST = topics
    SRC_LIST = iso_topic{}
    -> METADATA_VALUE_MAPPER_NG_12 [DATA_INPUT]
METADATA_VALUE_MAPPER_NG_12
    ATT_TO_MAP = topics{}.topic_value
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUPTABLES_DIR)
    P-T_ABBR = $(P-T_ABBR)
    -> AttributeExposer_8
AttributeExposer_8
    ATTR_TABLE = topics{}.topic_value,
    -> ListDuplicateRemover
ListDuplicateRemover
    SRC_LIST = topics{}.topic_value
    -> AttributeExposer_10

Bookmark: SUBJECTS value mapper from iso_topic{}.topic_value list attributes
AttributeExposer_10
    ATTR_TABLE = iso_topic{}.topic_value,
    -> ListCopier_3
ListCopier_3
    DEST_LIST = subjects
    SRC_LIST = iso_topic{}
    -> METADATA_VALUE_MAPPER_NG_13 [DATA_INPUT]
METADATA_VALUE_MAPPER_NG_13
    ATT_TO_MAP = subjects{}.topic_value
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUPTABLES_DIR)
    P-T_ABBR = $(P-T_ABBR)
    -> AttributeExposer_9
AttributeExposer_9
    ATTR_TABLE = subjects{}.topic_value,
    -> ListDuplicateRemover_2
ListDuplicateRemover_2
    SRC_LIST = subjects{}.topic_value
    -> METADATA_VALUE_MAPPER_ERROR_MANAGER_2

Bookmark: metadata delta finder
METADATA_DELTA_FINDER_GEN_2
    ATTR_DATE_MODIFIED = record_last_modified
    LOCAL_SOURCE = Yes
    METADATA_OVERWRITE = $(METADATA_OVERWRITE)
    METADATA_TYPE = JSON-CKANExtCa
    SOURCE_DIRECTORY = $(OUT_JSON_LOCAL_DIR)
    VALIDATE_INSERT_PCT = $(VALIDATE_INSERT_PCT_JSON)
    YAML_FILE = $(IN_CSV_LOOKUP_TABLES_DIR)\$(P-T_ABBR)\metadata_delta_finder_$(P-T_ABBR)_non_geo.yaml
    Statistics -> StatisticsCalculator_Summary_3
    Update -> Junction_7
    Insert -> Junction_7
    Delete -> AttributeExposer_14
Note: Log statistics
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
Junction_7
    -> AWS_TRANSLATE_3
AttributeExposer_14
    ATTR_TABLE = id,,title,
    -> DELETED_RECORDS_NONE_GEO (writer XLSXW_1)
Note: Log deleted features
DELETED_RECORDS_NONE_GEO (writer XLSXW_1)
    attributes: id string(200), title string(200)

Bookmark: JSON creation and writing
JSON_PUBLISHER_NG
    FEATURE_TYPE = JSON_CONFIG_$(P-T_ABBR)
    IN_CSV_LOOKUP_TABLES_DIR = $(IN_CSV_LOOKUPTABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = default_keyword
    Keywords_FR = default_keyword_fr
    P-T_ABBR = $(P-T_ABBR)
    Subject_LIST = subjects{}.topic_value
    Topic_LIST = topics{}.topic_value
    OUTPUT_LOCAL -> AttributeExposer_11
AttributeExposer_11
    ATTR_TABLE = json_file,,id,
    -> AttributeCreator_6
AttributeCreator_6
    ATTR_TABLE = SET_TO text_line_data (varchar(200)) = @Value(json_file)
    -> text_line (writer TEXTLINE_4)
text_line (writer TEXTLINE_4)
    attributes: text_line_data buffer
