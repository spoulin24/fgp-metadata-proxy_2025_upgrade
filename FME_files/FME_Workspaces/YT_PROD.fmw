FME workspace YT_PROD.fmw

Parameters:
- ACTIVATE_GEO = Yes
- ACTIVATE_NON_GEO = Yes
- ACTIVATE_TRANSLATION = No
- CATALOGUE_READER_SELECT = Yes
- FORCED_PYCSW_URL =
- IN_FFS_TESTING_FILE =
- LOCAL_SOURCE_METADATA_DELTA_FINDER = Yes
- LOCAL_WRITER = Yes
- METADATA_OVERWRITE = YES   # METADATA OVERWRITE
- SAMPLE_SIZE = 0
- IN_OUT_WORKING_DIR = $(FME_SHAREDRESOURCE_DATA)\PT_Harvester
- URL_VALIDATION = Yes
- VALIDATE_INSERT_PCT_XML = No
- VALIDATE_INSERT_PCT_JSON = No
- FME_USER_PARAM_PRIVATE_GRP =   # Private Parameters
- IN_CSV_LOOKUP_TABLES_DIR = $(IN_OUT_WORKING_DIR)\LOOKUP_TABLES
- IN_GMD_XML_TEMPLATE_DIR = $(IN_OUT_WORKING_DIR)\XML_TEMPLATES
- OUT_XML_LOCAL_DIR = $(IN_OUT_WORKING_DIR)\$(P-T_ABBR)\XML_LOCAL
- OUT_XML_FAILED_DIR = $(IN_OUT_WORKING_DIR)\$(P-T_ABBR)\XML_FAILED
- OUT_XML_PASSED_DIR = $(IN_OUT_WORKING_DIR)\$(P-T_ABBR)\XML_PASSED
- OUT_JSON_LOCAL_DIR = $(IN_OUT_WORKING_DIR)\$(P-T_ABBR)\JSON_LOCAL
- OUT_XLS_NOTIFICATION_DIR = $(IN_OUT_WORKING_DIR)\$(P-T_ABBR)\XLS
- LOG_FILE = $(IN_OUT_WORKING_DIR)\$(P-T_ABBR)\LOG\$(P-T_ABBR).log
- FME_SHAREDRESOURCE_DATA = C:\Data   # FME Flow Data Directory

Writers:
- TEXTLINE_1: TEXTLINE to $(OUT_XML_PASSED_DIR)
- TEXTLINE_2: TEXTLINE to $(OUT_XML_FAILED_DIR)
- TEXTLINE_3: TEXTLINE to $(OUT_XML_LOCAL_DIR)
- TEXTLINE_4: TEXTLINE to $(OUT_JSON_LOCAL_DIR)
- XLSXW_1: XLSXW to $(IN_OUT_WORKING_DIR)

SPATIAL_TYPE_NOT_MAPPED (writer XLSXW_1)
    attributes: id string(200), title string(200)
Note: Select Geo
Tester_6
    BOOL_OP = OR
    TEST_CLAUSE = TEST $(ACTIVATE_GEO) = Yes
    TEST_MODE = TEST
    PASSED -> TestFilter
Note: Select Non-Geo
Tester_2
    BOOL_OP = OR
    TEST_CLAUSE = TEST $(ACTIVATE_NON_GEO) = Yes
    TEST_MODE = TEST
    PASSED -> TestFilter_2

Bookmark: Metadata_Reader
Creator
    GEOMTYPE = Geometry Object
    NUM = 1
    CREATED -> DateTimeStamper
DateTimeStamper
    DATETIME_ATTR = _toto
    INCLUDE_FRAC_SECONDS = YES
    SCOPE = feature
    STAMP_TYPE = date
    TIMEZONE = local
    -> VariableSetter
VariableSetter
    SCOPE = Global
    VALUE = @Value(_toto)
    VARNAME = _timestamp
    -> Tester_3
Tester_3
    BOOL_OP = OR
    TEST_CLAUSE = CASE_INSENSITIVE_TEST $(CATALOGUE_READER_SELECT) = Yes
    TEST_MODE = CASE_INSENSITIVE_TEST
    PASSED -> Catalogue_Reader_YT_CKAN
    FAILED -> FeatureReader [INITIATOR]
Catalogue_Reader_YT_CKAN: Catalogue Reader_YT_CKAN
    CUSTOM_CSW_LIST_NAME = MD_Metadata{}
    CUSTOM_CSW_VERSION = 2.11
    CUSTOM_URL = https://open.yukon.ca/api/3/action
    SOURCE_URL = Manuel
    Résultats -> ATTRIBUTE_VALUE_TEXT_CLEANER_NG
Note: Reads pre-generated FFS file for testing as substitute for YT_CATALOGUE_READER
FeatureReader
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> ATTRIBUTE_VALUE_TEXT_CLEANER_NG

Bookmark: Open License filtering
Note: Removes whitespace from attributes except for the notes
ATTRIBUTE_VALUE_TEXT_CLEANER_NG
    IN_ATTR_TO_SKIP = notes
    -> AttributeExposer_3
AttributeExposer_3
    ATTR_TABLE = license_title,
    -> Tester
Tester
    BOOL_OP = OR
    TEST_CLAUSE = TEST @Value(license_title) != ""
    TEST_MODE = TEST
    PASSED -> LICENSE_FILTER_NG
    FAILED -> AttributeExposer_9
LICENSE_FILTER_NG
    FEATURE_TYPE = License_YT
    IN_CSV_LOOKUP_TABLES_DIR = $(IN_CSV_LOOKUP_TABLES_DIR)
    LICENSE_ATT = @Value(license_title)
    P-T_ABBR = $(P-T_ABBR)
    LICENSE_FILTER_PASSED -> URL_HTTPS_MAKER_NO_RESOURCES [UUIDGenerator_Input]
    UNKNOWN_LICENSE -> UNKNOWN_LICENCE (writer XLSXW_1)
UNKNOWN_LICENCE (writer XLSXW_1)
    attributes: id string(200), license_id string(200), license_title string(200)
AttributeExposer_9
    ATTR_TABLE = url,,id,
    -> DATASET_WITHOUT_LICENCE (writer XLSXW_1)
DATASET_WITHOUT_LICENCE (writer XLSXW_1)
    attributes: id string(200), license_title string(200), url string(200)

Bookmark: Formatting dates, missing attributes and contacts
URL_HTTPS_MAKER_NO_RESOURCES
    P-T_ABBR = $(P-T_ABBR)
    URL_VALIDATION = Yes
    -> AttributeExposer_16
Note: Sets date values to iso yyyy-mm-dd format
YT_DATE_FORMATTER
    -> DEFAULT_ATTRIBUTE_MAPPER_NG
    Invalid_date_format -> AttributeExposer_4
DEFAULT_ATTRIBUTE_MAPPER_NG
    FEATURE_TYPE = Default_YT
    IN_CSV_LOOKUP_TABLES_DIR = $(IN_CSV_LOOKUP_TABLES_DIR)
    P-T_ABBR = $(P-T_ABBR)
    -> YT_CONTACTS_MERGER
YT_CONTACTS_MERGER
    -> ATTRIBUTE_MANAGER_NG
ATTRIBUTE_MANAGER_NG
    IN_YAML_TEXT:
      notes:
          action: attribute_not_null
          attr2set: title

      iso_topic{}.topic_value:
          action: attribute_not_null
          attr2set: default_iso_topic

      east_bound_longitude:
          action: attribute_not_null
          attr2set: default_east_bound_longitude

      north_bound_latitude:
          action: attribute_not_null
          attr2set: default_north_bound_latitude

      south_bound_latitude:
          action: attribute_not_null
          attr2set: default_south_bound_latitude

      west_bound_longitude:
          action: attribute_not_null
          attr2set: default_west_bound_longitude

      progress_code:
          action: attribute_not_null
          attr2set: default_progress_code

      resource_update_cycle:
          action: attribute_not_null
          attr2set: default_resource_update_cycle

      spatialref_projection_name:
          action: attribute_not_null
          attr2set: default_spatialref_projection_name

      spatialref_projection_system:
          action: attribute_not_null
          attr2set: default_spatialref_projection_system

      spatialref_projection_system_version:
          action: attribute_not_null
          attr2set: default_spatialref_projection_system_version

      publisher:
          action: attribute_not_null
          attr2set: default_publisher

      tags{}.name:
          action: attribute_not_null
          attr2set: default_tags_display_name
    -> RESOURCES_VALIDATOR
Note: Validates url, name and format on resources{} list items
RESOURCES_VALIDATOR
    -> RESOURCE_NAME_UNDERSCORE_REMOVER_2
Note: Removes all underscores from resources{}.name attributes. Long compounded names joined by underscores in this field can cause display formatting issues when published to the FGP.
RESOURCE_NAME_UNDERSCORE_REMOVER_2
    DATA_OUTPUT -> AttributeExposer_6
AttributeExposer_4
    ATTR_TABLE = id,
    -> INVALID_DATE_FORMAT (writer XLSXW_1)
INVALID_DATE_FORMAT (writer XLSXW_1)
    attributes: id string(200), date_created string(200), date_published string(200), fme_rejection_code string(20)
UNKNOWN_MIME_TYPE (writer XLSXW_1)
    attributes: id string(200), _unknown_mime_type string(200), _url_validation string(200)

Bookmark: On retire la valeur du format car peu significatif
AttributeExposer_16
    ATTR_TABLE = resources{}.format,
    -> AttributeRemover
AttributeRemover
    LIST_ATTRS = resources{}.format
    -> ATTRIBUTE_MANAGER_NG_6
ATTRIBUTE_MANAGER_NG_6
    IN_YAML_TEXT:
      resources{}.format:
         action: attribute_overwrite
         attr2set: <missing>
    -> PythonCaller_4

Bookmark: On cherche le format des resources
Note: Ajustement, spécifique au Yukon pour les services web dans AGOL.
PythonCaller_4
    PYTHONSOURCE:
      import fme
      import fmeobjects
      from Python.FME_utils import FME_utils
      import re

      # Template Class Interface:
      class FeatureProcessor(object):
          def __init__(self):
              """Constructor of the class.
              Creates the logger to log information in FME log.
              """
              self.logger = fmeobjects.FMELogFile()

          def input(self, feature):
              BASE_URL = "https://yukon.maps.arcgis.com/"
              ID_PATTERN = r"item\.html\?id=([\w-]+)$"

              try:
                  session = FME_utils.create_session()
                  max_index = FME_utils.max_index_attribute_list(feature, 'resources{}.url')
              except Exception as e:
                  self.logger.logMessageString(f"[ERROR] Failed to initialize session or find max_index: {e}", fmeobjects.FME_ERROR)
                  self.pyoutput(feature)
                  return

              for j in range(max_index + 1):
                  try:
                      url = feature.getAttribute('resources{%i}.url'%(j))

                      if not url:
                          continue

                      match = re.search(ID_PATTERN, url)

                      if url.startswith(BASE_URL) and match:
                          item_id = match.group(1)
                          url_json_return = f"{BASE_URL}sharing/rest/content/items/{item_id}?f=json"

                          try:
                              response = FME_utils.make_http_call(self, feature, session, url_json_return, False)
                              json_data = response.json()
                              url_value = json_data.get('url')

                              if url_value:
                                  feature.setAttribute('resources{%i}.url'%(j), url_value )
                              else:
                                  self.logger.logMessageString(f"[WARNING] No 'url' field found in JSON for {url_json_return}", fmeobjects.FME_WARN)

                          except Exception as e_http:
                              self.logger.logMessageString(f"[ERROR] HTTP/JSON failure for {url_json_return}: {e_http}", fmeobjects.FME_ERROR)
                              continue
                      # If URL does not match pattern, silently skip
                  except Exception as e_loop:
                      self.logger.logMessageString(f"[ERROR] Unexpected error while processing resource index {j}: {e_loop}", fmeobjects.FME_ERROR)
                      continue

              self.pyoutput(feature)

          def close(self):
              pass
    PYTHONSYMBOL = FeatureProcessor
    -> PythonCaller_2
Note: If format = WMS or EsriRest; remove format value so that it is added in empty format mapper ng; to ensure that only valid WMS or EsriRest format are added
PythonCaller_2
    PYTHONSOURCE:
      import fme
      import fmeobjects
      from Python.FME_utils import FME_utils

      #def processFeature(feature):
      #    pass

      # Template Class Interface:
      # When using this class, make sure its name is set as the value of
      # the 'Class or Function to Process Features' transformer parameter
      def FeatureProcessor(feature):

          max_index=FME_utils.max_index_attribute_list(feature,'resources{}.format')
          for j in range(max_index+1):
              x = feature.getAttribute('resources{%i}.format'%(j))
              url = feature.getAttribute('resources{%i}.url'%(j))

              if url:
                  if url.endswith('service=WMS') or url.endswith('MapServer') or url.endswith('MapServer/WMS') or url.endswith('MapServer/') or url.endswith('WMS')or url.endswith('FeatureServer'):
                      feature.setAttributeNullWithType('resources{%i}.format'%(j),fmeobjects.FME_ATTR_ENCODED_STRING)

              elif x:
                  if x.upper() == 'ESRI REST' or x.upper() == 'WMS' :
                      feature.setAttributeNullWithType('resources{%i}.format'%(j),fmeobjects.FME_ATTR_ENCODED_STRING)
    PYTHONSYMBOL = FeatureProcessor
    -> EMPTY_FORMAT_MAPPER_NG_2 [DATA_INPUT]
EMPTY_FORMAT_MAPPER_NG_2
    CSV_FORMAT = Format
    CSV_MIME_TYPE = Mime_type
    IN_CSV_LOOKUP_TABLES_DIR = $(IN_CSV_LOOKUP_TABLES_DIR)
    P-T_ABBR = $(P-T_ABBR)
    URL_VALIDATION = $(URL_VALIDATION)
    DATA_OUTPUT -> YT_DATE_FORMATTER
    UNKNOWN_MIME_TYPE -> UNKNOWN_MIME_TYPE (writer XLSXW_1)

Bookmark: On crée l'url de la metadatt original
AttributeExposer_6
    ATTR_TABLE = url,,type,,id,
    -> StringConcatenator
StringConcatenator
    ACTION = Overwrite Existing Attributes
    ATTRLIST = url
    PARM_LINE = fme_basicstring:45:https://open.yukon.ca/@Value(type)/@Value(id)
    -> GEOPORTAL_WEBLINK_ADDER_NG

Bookmark: Adding weblink
GEOPORTAL_WEBLINK_ADDER_NG
    FEATURE_TYPE = GeoportalWeblink_YT
    IN_CSV_LOOKUP_TABLES_DIR = $(IN_CSV_LOOKUP_TABLES_DIR)
    P-T_ABBR = $(P-T_ABBR)
    URL_VALIDATION = $(URL_VALIDATION)
    WEBLINK_WILDCARD = @Value(url)
    -> AttributeExposer_22

Bookmark: Ajusting and verifying contact{}.email
AttributeExposer_22
    ATTR_TABLE = contacts{0}.email,
    -> EMAIL_FORMAT_TESTER_2
EMAIL_FORMAT_TESTER_2
    DEFAULT_CONTACT_EMAIL = @Value(contacts{0}.email)
    -> METADATA_VALUE_MAPPER_NG_7 [DATA_INPUT]
Note: contacts{}.email
METADATA_VALUE_MAPPER_NG_7
    ATT_TO_MAP = contacts{}.email
    CODE_REFRESH = NO
    ENGLISH_REFRESH = YES
    ERROR_NOT_MAPPED = NO
    FEATURE_TYPE = Email
    FRENCH_REFRESH = NO
    IN_CSV_LOOKUP_TABLES_DIR = $(IN_CSV_LOOKUP_TABLES_DIR)
    P-T_ABBR = $(P-T_ABBR)
    -> AttributeExposer_25

Bookmark: GEstion des tages
AttributeExposer_25
    ATTR_TABLE = tags{}.name,
    -> ListDuplicateRemover_2
Note: Removes duplicates from tags{} list attribute
ListDuplicateRemover_2
    SRC_LIST = tags{}.name
    -> ATTRIBUTE_MAPPER_AND_LENGTH_CHECKER [INPUT_2]
ATTRIBUTE_MAPPER_AND_LENGTH_CHECKER
    CODE_REFRESH = NO
    ENGLISH_REFRESH = YES
    ERROR_NOT_MAPPED = NO
    FEATURE_TYPE = tags_name_long
    FRENCH_REFRESH = NO
    IN_ATT_TO_MAP = tags{}.name
    IN_CHAR_LIMIT = 120
    IN_CSV_LOOKUP_TABLES_DIR = $(IN_CSV_LOOKUP_TABLES_DIR)
    P-T_ABBR = $(P-T_ABBR)
    CORRECT_LENGTH -> GEO_NONE_GEO_SELECTOR_6
    TOO_LONG -> ListExploder
ListExploder
    ATTR_CONFLICT_RES_LOOKUP = INCOMING_IF_CONFLICT
    INDEX_ATTR = _element_index
    LIST_ATTR = _to_long_value{}
    ATTR_ACCUM_MODE = Merge List Attributes
    ATTR_CONFLICT_RES = Use List Attribute Values
    ELEMENTS -> DuplicateFilter
DuplicateFilter
    INPUT_ORDERED_CHOICE_LOOKUP = NO
    KEYATTR = _to_long_value
    INPUT_ORDERED_CHOICE = No
    UNIQUE -> ATTRIBUTE_LENGTH_CHECKER_INFO (writer XLSXW_1)
ATTRIBUTE_LENGTH_CHECKER_INFO (writer XLSXW_1)
    attributes: id string(200), _to_long_value string(200), _to_long_value_concatenated string(200)

Bookmark: Geospatial/non-geospatial data filtering
Note: Recherche dans les formats
GEO_NONE_GEO_SELECTOR_6
    CSV_FILE_NAME = GeoSpatialValidation
    CSV_PATH = $(IN_CSV_LOOKUP_TABLES_DIR)
    CSV_PROVINCE = $(P-T_ABBR)
    YAML_DIRECTIVES:
      #resources{}.format:
      #   domain: lookup_table_format
      #   spatial_type: overwrite
      #   not_found: log
      #   search_type: equals
      #
      resources{}.description:
         domain: lookup_table_format
         spatial_type: overwrite
         not_found: no_log
         search_type: contains
      #
      resources{}.name:
         domain: lookup_table_format
         spatial_type: overwrite
         not_found: no_log
         search_type: contains
    GEOSPATIAL -> AttributeExposer_18
    NONE_GEOSPATIAL -> GEO_NONE_GEO_SELECTOR_3
    LOG_ERROR -> GEOSPATIAL_FORMAT_NOT_MAPPED (writer XLSXW_1)
Note: Recherche dans les noms pour valeur fixe
GEO_NONE_GEO_SELECTOR_3
    CSV_FILE_NAME = GeoSpatialValidation
    CSV_PATH = $(IN_CSV_LOOKUP_TABLES_DIR)
    CSV_PROVINCE = $(P-T_ABBR)
    YAML_DIRECTIVES:
      resources{}.name:
         domain: [ISO 19139 Geographic Information, "Map Package", Geotiffs]
         spatial_type: no_overwrite
         not_found: no_log
         search_type: contains
    GEOSPATIAL -> AttributeExposer_18
    NONE_GEOSPATIAL -> GEO_NONE_GEO_SELECTOR_5
    LOG_ERROR -> GEOSPATIAL_FORMAT_NOT_MAPPED (writer XLSXW_1)
Note: Recherche description des resources
GEO_NONE_GEO_SELECTOR_5
    CSV_FILE_NAME = GeoSpatialValidation
    CSV_PATH = $(IN_CSV_LOOKUP_TABLES_DIR)
    CSV_PROVINCE = $(P-T_ABBR)
    YAML_DIRECTIVES:
      resources{}.description:
         domain: ["GDB,", "SHP,", "KMZ,", "gdb,", "shp,", "kmz,", MXD, "MXD,", mxd, "mxd,", geodatabase, Geodatabase, shapefile, Shapefile, "web map"]
         spatial_type: no_overwrite
         not_found: no_log
         search_type: contains
    GEOSPATIAL -> AttributeExposer_18
    NONE_GEOSPATIAL -> MANUAL_GEOSPATIAL_SETTER_NG [DATA_INPUT]
    LOG_ERROR -> GEOSPATIAL_FORMAT_NOT_MAPPED (writer XLSXW_1)
MANUAL_GEOSPATIAL_SETTER_NG
    FEATURE_TYPE = UnmappedGeodata_YT
    IN_CSV_LOOKUP_TABLES_DIR = $(IN_CSV_LOOKUP_TABLES_DIR)
    P-T_ABBR = $(P-T_ABBR)
    GEOSPATIAL -> Tester_6
    NON-GEOSPATIAL -> Tester_2
    UNMAPPED_DATA -> UNMAPPED_GEODATA_YT (writer XLSXW_1)
UNMAPPED_GEODATA_YT (writer XLSXW_1)
    attributes: id string(200), notes string(200), title string(200), url string(200)
GEOSPATIAL_FORMAT_NOT_MAPPED (writer XLSXW_1)
    attributes: id string(200), _geo_none_geo_status string(200), _not_found_err_msg string(200), format string(200)
SPATIAL_TYPE_MAPPER_NG
    FEATURE_TYPE = UUID_Spatial_YT
    IN_CSV_LOOKUP_TABLES_DIR = $(IN_CSV_LOOKUP_TABLES_DIR)
    P-T_ABBR = $(P-T_ABBR)
    DATA_OUTPUT_FAILED -> AttributeExposer_2
    DATA_OUTPUT_PASSED -> Tester_6
AttributeExposer_2
    ATTR_TABLE = id,,title,
    -> SPATIAL_TYPE_NOT_MAPPED (writer XLSXW_1)

Bookmark: Remettre en non géo les uuids fautifs. Des fois nos mots clés confondes le géo et le non géo
AttributeExposer_18
    ATTR_TABLE = id,
    -> FeatureMerger_2 [REQUESTOR]
LOOKUP_TABLES_READER_NG
    CSV_ENCODING = utf-8
    CSV_PATH = $(IN_CSV_LOOKUP_TABLES_DIR)
    FEATURE_TYPE = UUID_2set_nongeo
    PT = $(P-T_ABBR)
    -> AttributeExposer_13
AttributeExposer_13
    ATTR_TABLE = id,
    -> FeatureMerger_2 [SUPPLIER]
FeatureMerger_2
    ATTR_ACCUM_MODE = Merge Supplier
    ATTR_CONFLICT_RES_LOOKUP = REQUESTOR_IF_CONFLICT
    IGNORE_NULLS = No
    JOIN_KEYS = @Value(id) @Value(id) AUTO
    MERGE_TYPE_VAL = ATTRIBUTES
    PROCESS_DUPS = NO
    REJECT_NULL_MISSING_KEYS = No
    SUPPLIERS_FIRST = No
    ATTR_CONFLICT_RES = Use Requestor
    MERGE_TYPE = Attributes Only
    MERGED -> Tester_2
    UNMERGED_REQUESTOR -> SPATIAL_TYPE_MAPPER_NG [DATA_INPUT]

Bookmark: Samples or full content
TestFilter
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> FORMAT_VALIDATOR
    SAMPLES FEATURES -> Sampler_3
Sampler_3
    MODE = ORIGINAL
    RATE = $(SAMPLE_SIZE)
    SAMPLE_TYPE_MULTIPLIER = -1
    SAMPLE_MODE = No
    SAMPLE_TYPE_LONG = First N Features
    SAMPLED -> FORMAT_VALIDATOR

Bookmark: Attribute Validation
Note: Verfication if URL is valid WMS call for WMS formats
FORMAT_VALIDATOR
    -> METADATA_VALUE_MAPPER_NG [DATA_INPUT]

Bookmark: Attribute value mapper
Note: iso_topic{}.topic_value
METADATA_VALUE_MAPPER_NG
    ATT_TO_MAP = iso_topic{}.topic_value
    CODE_REFRESH = NO
    ENGLISH_REFRESH = YES
    ERROR_NOT_MAPPED = YES
    FEATURE_TYPE = Keyword
    FRENCH_REFRESH = NO
    IN_CSV_LOOKUP_TABLES_DIR = $(IN_CSV_LOOKUP_TABLES_DIR)
    P-T_ABBR = $(P-T_ABBR)
    -> METADATA_VALUE_MAPPER_NG_2 [DATA_INPUT]
Note: contacts{}.role
METADATA_VALUE_MAPPER_NG_2
    ATT_TO_MAP = contacts{}.role
    CODE_REFRESH = YES
    ENGLISH_REFRESH = YES
    ERROR_NOT_MAPPED = YES
    FEATURE_TYPE = role
    FRENCH_REFRESH = YES
    IN_CSV_LOOKUP_TABLES_DIR = $(IN_CSV_LOOKUP_TABLES_DIR)
    P-T_ABBR = $(P-T_ABBR)
    -> METADATA_VALUE_MAPPER_NG_3 [DATA_INPUT]
Note: spatial_representation_type
METADATA_VALUE_MAPPER_NG_3
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = $(P-T_ABBR)
    -> METADATA_VALUE_MAPPER_NG_4 [DATA_INPUT]
Note: progress_code
METADATA_VALUE_MAPPER_NG_4
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = $(P-T_ABBR)
    -> METADATA_VALUE_MAPPER_NG_5 [DATA_INPUT]
Note: spatailref_projection_name
METADATA_VALUE_MAPPER_NG_5
    ATT_TO_MAP = spatialref_projection_name
    CODE_REFRESH = NO
    ENGLISH_REFRESH = YES
    ERROR_NOT_MAPPED = YES
    FEATURE_TYPE = SpatialRef
    FRENCH_REFRESH = NO
    IN_CSV_LOOKUP_TABLES_DIR = $(IN_CSV_LOOKUP_TABLES_DIR)
    P-T_ABBR = $(P-T_ABBR)
    -> METADATA_VALUE_MAPPER_NG_6 [DATA_INPUT]
Note: resource_update_cycle
METADATA_VALUE_MAPPER_NG_6
    ATT_TO_MAP = resource_update_cycle
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = $(P-T_ABBR)
    -> METADATA_FORMAT_MAPPER_NG [DATA_INPUT]

Bookmark: Format value mapper
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_Geo (writer XLSXW_1)
    -> METADATA_VALUE_MAPPER_ERROR_MANAGER
UNKNOWN_MIME_TYPE_Geo (writer XLSXW_1)
    attributes: _unknown_mime_type string(8), _url_validation string(8), id string(8)

Bookmark: Mapping error list creator
METADATA_VALUE_MAPPER_ERROR_MANAGER
    ERROR_OUTPUT -> METADATA_MAPPING_ERRORS (writer XLSXW_1)
    DATA_OUTPUT -> MORE_INFO_MANAGER
METADATA_MAPPING_ERRORS (writer XLSXW_1)
    attributes: id string(200), error string(200), _element_index string(200)

Bookmark: Data preparation for metadata section
Note: Tests the more_info{}.link list for valid attribute values and filters them out where missing
MORE_INFO_MANAGER
    -> REMOVE_BROKEN_URL_WMS_ESRI_REST

Bookmark: Data cleanup. Dropping broken web services
REMOVE_BROKEN_URL_WMS_ESRI_REST
    URL_VALIDATION = Yes
    -> WMS_REST_LANGUAGE_FORMATTER
    FAULTY_URL_OUTPUT -> MAP_SERVICE_URL_ERROR (writer XLSXW_1)
MAP_SERVICE_URL_ERROR (writer XLSXW_1)
    attributes: id string(200), url string(200), format string(200), _url_failure_message string(200)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> GMD_SECTION_DATA_EXTRACTION

Bookmark: List and duplicate cleanup
Note: Creates lists and removes duplicates for GMD_Section
GMD_SECTION_DATA_EXTRACTION
    -> AttributeExposer

Bookmark: Arrondir le bbox
AttributeExposer
    ATTR_TABLE = east_bound_longitude,,north_bound_latitude,,south_bound_latitude,,west_bound_longitude,
    -> AttributeRounder
AttributeRounder
    PLACES = 7
    ROUND_TYPE_TCL = round
    SRC_ATTRS = east_bound_longitude north_bound_latitude south_bound_latitude west_bound_longitude
    ROUND_TYPE = Nearest
    -> AttributeCreator_3

Bookmark: Configuring publishing info
AttributeCreator_3
    ATTR_TABLE = SET_TO csw_url (varchar(200)) = $(FORCED_PYCSW_URL)
    -> ATTRIBUTE_MANAGER_NG_4
AttributeExposer_20
    ATTR_TABLE = search_criteria_pycsw,,csw_url,,record_last_modified,,id,
    -> METADATA_DELTA_FINDER_GEN
METADATA_DELTA_FINDER_GEN
    ATTR_DATE_MODIFIED = record_last_modified
    CSW_FILTER = @Value(search_criteria_pycsw)
    LOCAL_SOURCE = $(LOCAL_SOURCE_METADATA_DELTA_FINDER)
    METADATA_OVERWRITE = $(METADATA_OVERWRITE)
    METADATA_TYPE = XML-HNAP
    SOURCE_DIRECTORY = $(OUT_XML_LOCAL_DIR)
    SOURCE_URL = @Value(csw_url)
    VALIDATE_INSERT_PCT = $(VALIDATE_INSERT_PCT_XML)
    YAML_FILE = $(IN_CSV_LOOKUP_TABLES_DIR)\$(P-T_ABBR)\metadata_delta_finder_$(P-T_ABBR)_geo.yaml
    Statistics -> StatisticsCalculator_Summary_2
    No_Change -> METADATA_DELTA_FINDER_GEN_No_Change
    Update -> AWS_TRANSLATE
    Update -> METADATA_DELTA_FINDER_GEN_Update
    Insert -> AWS_TRANSLATE
    Insert -> METADATA_DELTA_FINDER_GEN_Insert
    Delete -> AttributeExposer_10
    Delete -> METADATA_DELTA_FINDER_GEN_Delete
Note: Log statistics
StatisticsCalculator_Summary_2: Logger
    LOG_FEATURE = NONE
    MAXFEATS = 20
    MESSAGE:
      ************************
      **** NoneGeo Features: Unchanged Report ****
      ************************

      @Value(_real_count) features were unchanged

      ************************
      ************************
      ************************
    SEVERITY = INFO
METADATA_DELTA_FINDER_GEN_No_Change: Logger
    LOG_FEATURE = LOG_ONLY
    MAXCOORDS = 20
    MAXFEATS = 20
    MESSAGE = Feature is:
    SEVERITY = INFO
AttributeExposer_10
    ATTR_TABLE = id,
    -> AttributeKeeper_3
Note: Retains ID for list of deleted items
AttributeKeeper_3
    CREATE_BULK_MODE_FEATURES = No
    KEEP_ATTRS = id
    -> DELETED_RECORDS01 (writer XLSXW_1)
DELETED_RECORDS01 (writer XLSXW_1)
    attributes: id string(200)
METADATA_DELTA_FINDER_GEN_Update: Logger
    LOG_FEATURE = LOG_ONLY
    MAXCOORDS = 20
    MAXFEATS = 20
    MESSAGE = Feature is:
    SEVERITY = INFO
METADATA_DELTA_FINDER_GEN_Insert: Logger
    LOG_FEATURE = LOG_ONLY
    MAXCOORDS = 20
    MAXFEATS = 20
    MESSAGE = Feature is:
    SEVERITY = INFO
METADATA_DELTA_FINDER_GEN_Delete: Logger
    LOG_FEATURE = LOG_ONLY
    MAXCOORDS = 20
    MAXFEATS = 20
    MESSAGE = Feature is:
    SEVERITY = INFO

Bookmark: Listes Metadata_delta_finder
ATTRIBUTE_MANAGER_NG_4
    IN_YAML_TEXT:
      contacts{0}.role_code:
         action: attribute_not_null
         attr2set: role_code
      contacts{0}.role:
         action: attribute_not_null
         attr2set: role
      contacts{0}.role_fr:
         action: attribute_not_null
         attr2set: role_fr
      contacts{0}.p-t_entity:
         action: attribute_not_null
         attr2set: p-t_entity
      contacts{0}.p-t_entity_fr:
         action: attribute_not_null
         attr2set: p-t_entity_fr
      contacts{0}.sector:
         action: attribute_not_null
         attr2set: publisher
      contacts{0}.sector_fr:
         action: attribute_not_null
         attr2set: publisher
      contacts{0}.email:
         action: attribute_not_null
         attr2set: contact_email
      distributionList{0}.format_version:
         action: attribute_not_null
         attr2set: distribution_format_version
      resources{0}.language:
         action: attribute_not_null
         attr2set: transfer_option_description_language
      spatialref{0}.projection_name:
         action: attribute_not_null
         attr2set: spatialref_projection_name
      spatialref{0}.projection_system:
         action: attribute_not_null
         attr2set: spatialref_projection_system
      spatialref{0}.projection_system_version:
         action: attribute_not_null
         attr2set: spatialref_projection_system_version
    -> ATTRIBUTE_MANAGER_NG_5
ATTRIBUTE_MANAGER_NG_5
    IN_YAML_TEXT:
      contacts{}.role_code:
         action: attribute_not_null
         attr2set: role_code
      contacts{}.role:
         action: attribute_not_null
         attr2set: role
      contacts{}.role_fr:
         action: attribute_not_null
         attr2set: role_fr
      contacts{}.p-t_entity:
         action: attribute_not_null
         attr2set: p-t_entity
      contacts{}.p-t_entity_fr:
         action: attribute_not_null
         attr2set: p-t_entity_fr
      contacts{}.sector:
         action: attribute_not_null
         attr2set: publisher
      contacts{}.sector_fr:
         action: attribute_not_null
         attr2set: publisher
      contacts{}.email:
         action: attribute_not_null
         attr2set: contact_email
      distributionList{}.format_version:
         action: attribute_not_null
         attr2set: distribution_format_version
      resources{}.language:
         action: attribute_not_null
         attr2set: transfer_option_description_language
      spatialref{}.projection_name:
         action: attribute_not_null
         attr2set: spatialref_projection_name
      spatialref{}.projection_system:
         action: attribute_not_null
         attr2set: spatialref_projection_system
      spatialref{}.projection_system_version:
         action: attribute_not_null
         attr2set: spatialref_projection_system_version
    -> AttributeExposer_20

Bookmark: Language Translation
Note: Translates specific items from English to French
AWS_TRANSLATE
    ACTIVATE_TRANSLATION = $(ACTIVATE_TRANSLATION)
    ATTR_2_TRANSLATE = notes,title
    ATTR_LIST_2_TRANSLATE = tags{}.name,resources{}.name
    MODE = English-->French
    -> XML_PUBLISHER_NG
    TRANSLATION_PROBLEM -> TRANSLATION_PROBLEMS (writer XLSXW_1)
TRANSLATION_PROBLEMS (writer XLSXW_1)
    attributes: id string(200), _typedatasets string(200), _translation_status string(200)

Bookmark: XML CREATION AND WRITING
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
XML_PUBLISHER_NG
    FEATURE_TYPE = Config_$(P-T_ABBR)
    IN_CSV_LOOKUP_TABLES_DIR = $(IN_OUT_WORKING_DIR)\LOOKUP_TABLES
    LOCAL_WRITER = $(LOCAL_WRITER)
    P-T_ABBR = $(P-T_ABBR)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> INVALID_METADATA (writer XLSXW_1)
    UPDATE_FAILED -> text_line (writer TEXTLINE_2)
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer
INVALID_METADATA (writer XLSXW_1)
    attributes: id string(200)

Bookmark: Samples or full content
TestFilter_2
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> METADATA_VALUE_MAPPER_NG_8 [DATA_INPUT]
    SAMPLES FEATURES -> Sampler_4
Sampler_4
    MODE = ORIGINAL
    RATE = $(SAMPLE_SIZE)
    SAMPLE_TYPE_MULTIPLIER = -1
    SAMPLE_MODE = No
    SAMPLE_TYPE_LONG = First N Features
    SAMPLED -> METADATA_VALUE_MAPPER_NG_8 [DATA_INPUT]

Bookmark: Non-geo data processing
Note: resource_update_cycle
METADATA_VALUE_MAPPER_NG_8
    ATT_TO_MAP = resource_update_cycle
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = $(P-T_ABBR)
    -> AttributeExposer_19
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_NoneGeo (writer XLSXW_1)
    -> METADATA_VALUE_MAPPER_ERROR_MANAGER_2
UNKNOWN_MIME_TYPE_NoneGeo (writer XLSXW_1)
    attributes: _unknown_mime_type string(8), _url_validation string(8), id string(8)
Note: Manage maping errors
METADATA_VALUE_MAPPER_ERROR_MANAGER_2
    ERROR_OUTPUT -> NON_GEO_UNMAPPED_METADATA_VALUES (writer XLSXW_1)
    DATA_OUTPUT -> ATTRIBUTE_MANAGER_NG_2
Note: Writing errors into XLS spreadsheet
NON_GEO_UNMAPPED_METADATA_VALUES (writer XLSXW_1)
    attributes: error string(200), id string(200)
Note: Ajustement des tags/topic/subject / Ajout de valeur par défault si vide
ATTRIBUTE_MANAGER_NG_2
    IN_YAML_TEXT:
      TBS_Subject{0}.value:
          action: attribute_not_null
          attr2set: default_tbs_subject
      TBS_Topic{0}.value:
          action: attribute_not_null
          attr2set: default_tbs_topic
      tags{0}.display_name:
          action: attribute_not_null
          attr2set: default_tbs_tag
      resources{0}.language:
          action: attribute_not_null
          attr2set: transfer_option_description_language_TBS
    -> ATTRIBUTE_MANAGER_NG_3
Note: Valeur pour l'ensemble de la liste des resources{}.language
ATTRIBUTE_MANAGER_NG_3
    IN_YAML_TEXT:
      resources{}.language:
          action: attribute_not_null
          attr2set: transfer_option_description_language_TBS
    -> AttributeExposer_5
AttributeExposer_5
    ATTR_TABLE = record_last_modified,,id,
    -> METADATA_DELTA_FINDER_GEN_2
METADATA_DELTA_FINDER_GEN_2
    ATTR_DATE_MODIFIED = record_last_modified
    LOCAL_SOURCE = Yes
    METADATA_OVERWRITE = $(METADATA_OVERWRITE)
    METADATA_TYPE = JSON-CKANExtCa
    SOURCE_DIRECTORY = $(OUT_JSON_LOCAL_DIR)
    VALIDATE_INSERT_PCT = $(VALIDATE_INSERT_PCT_JSON)
    YAML_FILE = $(IN_CSV_LOOKUP_TABLES_DIR)\$(P-T_ABBR)\metadata_delta_finder_$(P-T_ABBR)_non_geo.yaml
    Statistics -> StatisticsCalculator_Summary_3
    Update -> AWS_TRANSLATE_4
    Insert -> AWS_TRANSLATE_4
    Delete -> AttributeExposer_7
Note: Log statistics
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
Note: Translating english to french notes, title, keyword (tags) and resources.name
AWS_TRANSLATE_4
    ACTIVATE_TRANSLATION = $(ACTIVATE_TRANSLATION)
    ATTR_2_TRANSLATE = notes,title
    ATTR_LIST_2_TRANSLATE = tags{}.name,resources{}.name
    MODE = English-->French
    -> JSON_PUBLISHER_NG
AttributeExposer_7
    ATTR_TABLE = id,
    -> AttributeKeeper_2
Note: Retains ID for list of deleted items
AttributeKeeper_2
    CREATE_BULK_MODE_FEATURES = No
    KEEP_ATTRS = id
    -> DELETED_RECORDS_NONE_GEO (writer XLSXW_1)
DELETED_RECORDS_NONE_GEO (writer XLSXW_1)
    attributes: id string(200)

Bookmark: Generating TBS_SUBJECT list based iso_topic
AttributeExposer_19
    ATTR_TABLE = iso_topic{}.topic_value,
    -> ListCopier
Note: Copy tags in TBS_Subject list
ListCopier
    DEST_LIST = TBS_Subject
    SRC_LIST = iso_topic{}
    -> METADATA_VALUE_MAPPER_NG_9 [DATA_INPUT]
Note: TBS_Subject{}value
METADATA_VALUE_MAPPER_NG_9
    ATT_TO_MAP = TBS_Subject{}.topic_value
    CODE_REFRESH = NO
    ENGLISH_REFRESH = YES
    ERROR_NOT_MAPPED = YES
    FEATURE_TYPE = Subject_TBS_YT
    FRENCH_REFRESH = NO
    IN_CSV_LOOKUP_TABLES_DIR = $(IN_CSV_LOOKUP_TABLES_DIR)
    P-T_ABBR = $(P-T_ABBR)
    -> AttributeExposer_27
Note: exposing list attribute
AttributeExposer_27
    ATTR_TABLE = TBS_Subject{}.topic_value,
    -> ListDuplicateRemover
Note: Removeing duplicates on subject value
ListDuplicateRemover
    SRC_LIST = TBS_Subject{}.topic_value
    -> AttributeExposer_28

Bookmark: Generating TBS Topic based on presets.yaml
Note: exposing attribute
AttributeExposer_28
    ATTR_TABLE = iso_topic{},
    -> ListCopier_2
Note: Copy tags in a temp list
ListCopier_2
    DEST_LIST = TBS_Topic
    SRC_LIST = iso_topic{}
    -> METADATA_VALUE_MAPPER_NG_10 [DATA_INPUT]
Note: TBS_Subject{}value
METADATA_VALUE_MAPPER_NG_10
    ATT_TO_MAP = TBS_Topic{}.topic_value
    CODE_REFRESH = NO
    ENGLISH_REFRESH = YES
    ERROR_NOT_MAPPED = YES
    FEATURE_TYPE = Topic_TBS_YT
    FRENCH_REFRESH = NO
    IN_CSV_LOOKUP_TABLES_DIR = $(IN_CSV_LOOKUP_TABLES_DIR)
    P-T_ABBR = $(P-T_ABBR)
    -> AttributeExposer_29
Note: exposing list attribute
AttributeExposer_29
    ATTR_TABLE = TBS_Topic{}.topic_value,
    -> PythonCaller_6
Note: Strip the default value in the lookup table named "No Topic"
PythonCaller_6
    PYTHONSOURCE:
      import fme
      import fmeobjects
      # Template Function interface:
      # When using this function, make sure its name is set as the value of
      # the 'Class or Function to Process Features' transformer parameter
      def processFeature(feature):
          pass

      # Template Class Interface:
      # When using this class, make sure its name is set as the value of
      # the 'Class or Function to Process Features' transformer parameter
      class FeatureProcessor(object):
          def __init__(self):
              pass

          def input(self,feature):
              topic = feature.getAttribute('TBS_Topic{}.topic_value')

              topic = [i for i in topic if i != 'No Topic']
              #print(topic)

              feature.removeAttribute('TBS_Topic{}.topic_value')
              feature.setAttribute('TBS_Topic{}.topic_value', topic)

              self.pyoutput(feature)

          def close(self):
              pass
    PYTHONSYMBOL = FeatureProcessor
    -> METADATA_FORMAT_MAPPER_NG_2 [DATA_INPUT]

Bookmark: Writing the JSON file into the specified dir
JSON_PUBLISHER_NG
    FEATURE_TYPE = JSON_CONFIG_$(P-T_ABBR)
    IN_CSV_LOOKUP_TABLES_DIR = $(IN_CSV_LOOKUP_TABLES_DIR)
    JSON_RESOURCE_TEMPLATE = $(IN_TBS_JSON_TEMPLATE_DIR:)\TBS_RESOURCES_TEMPLATE_NG.json
    JSON_ROOT_TEMPLATE = $(IN_TBS_JSON_TEMPLATE_DIR:)\TBS_ROOT_TEMPLATE_NG.json
    Keywords_EN = tags{}.name
    Keywords_FR = tags{}.name_fr
    P-T_ABBR = $(P-T_ABBR)
    Subject_LIST = TBS_Subject{}.topic_value
    Topic_LIST = TBS_Topic{}.topic_value
    OUTPUT_LOCAL -> AttributeExposer_26
AttributeExposer_26
    ATTR_TABLE = json_file,,id,
    -> AttributeCreator_7
AttributeCreator_7
    ATTR_TABLE = SET_TO text_line_data (varchar(200)) = @Value(json_file)
    -> text_line (writer TEXTLINE_4)
text_line (writer TEXTLINE_4)
    attributes: text_line_data buffer

Bookmark: Data extraction
Note: I was able to find the missing records manually in YT portal. We can use a lookup toable to map name to ID and read correctly missing records

Bookmark: Geospatial Export
Note: Writes mapping errors to Excel file
Note: Tests WMS/ESRI_REST resource URL's and removes them where broken
