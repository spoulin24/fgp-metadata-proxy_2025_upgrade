FME workspace QC_PROD.fmw
Title: QC_PROD
Description: Description 
This workbench read and trasform all the metadata for the province of Québec (QC)
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
CATALOGUE_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the CATALOGUE_READER. This file is used when the parameter: CATALOGUE_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
SAMPLE_SIZE: Number of features to process. Zero (0) means process all the features. A number n greater than 0 means sample or process only the first n features.
URL_VALIDATION : Indicates to validate or not created URL. (Should be Yes for prod)
VALIDATE_INSERT_PCT :Indicates to valide insert percentage. 75 % or less insert/update record  (Should be Yes for prod)
History: Unknown,Unknown,Original version,01/04/2022,Daniel Pilon,Code refactoring
Startup Python:
      import sys
      import fme
      try:
          if fme.macroValues['FME_SHAREDRESOURCE_DATA']:
              new_path='%s\PT_Harvester\Python'%(fme.macroValues['FME_SHAREDRESOURCE_DATA'])

              print ('Ajout de %s dans le path '%(new_path))
              sys.path += [new_path]


      except:
          raise

Parameters:
- ACTIVATE_GEO = Yes
- ACTIVATE_NON_GEO = yes
- ACTIVATE_TRANSLATION = Yes
- CATALOGUE_READER_SELECT = Yes
- FORCED_PYCSW_URL =
- IN_FFS_TESTING_FILE =
- LOCAL_SOURCE_METADATA_DELTA_FINDER = No
- LOCAL_WRITER = No
- METADATA_OVERWRITE = NO
- IN_OUT_WORKING_DIR = $(FME_SHAREDRESOURCE_DATA)\PT_Harvester
- SAMPLE_SIZE = 0
- URL_VALIDATION = Yes
- VALIDATE_INSERT_PCT_JSON = Yes
- VALIDATE_INSERT_PCT_XML = Yes
- IN_CSV_LOOKUP_TABLES_DIR = $(IN_OUT_WORKING_DIR)\LOOKUP_TABLES   # DEFAULT_IN_CSV_LOOKUP_TABLES_DIR
- IN_GMD_XML_TEMPLATE_DIR = $(IN_OUT_WORKING_DIR)\XML_TEMPLATES
- IN_TBS_JSON_TEMPLATE_DIR = $(IN_OUT_WORKING_DIR)\\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- FME_SHAREDRESOURCE_DATA = C:\Data   # FME Flow Data Directory

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(OUT_XLS_NOTIFICATION_DIR)
- TEXTLINE_4: TEXTLINE to $(OUT_JSON_LOCAL_DIR)

Junction_4
    -> QC_PROJECTION_GEOEXTENTS_EXTRACTOR
UNKNOWN_MIME_TYPE_Geo (writer XLSXW_1)
    attributes: _unknown_mime_type string(8), _url_validation string(8), id string(8)
Junction
    -> METADATA_VALUE_MAPPER_NG_4 [DATA_INPUT]
UNKNOWN_MIME_TYPE_NoneGeo (writer XLSXW_1)
    attributes: _unknown_mime_type string(8), _url_validation string(8), id string(8)
Note: Writes XML to a local folder without publishing to PyCSW, and without the PyCSW transaction headers and footers
text_line (writer TEXTLINE_3)
    attributes: text_line_data buffer
Note: Writes XML published to the PyCSW to a local folder
text_line (writer TEXTLINE_1)
    attributes: text_line_data buffer
Note: Writes XML that failed to publish to the PyCSW to a local folder
text_line (writer TEXTLINE_2)
    attributes: text_line_data buffer

Bookmark: Reading QC Geoportal datasets
Creator
    GEOMTYPE = Geometry Object
    NUM = 1
    CREATED -> Tester_3
Tester_3
    BOOL_OP = OR
    TEST_CLAUSE = TEST $(CATALOGUE_READER_SELECT) = Yes
    TEST_MODE = TEST
    PASSED -> Catalogue_Reader
    FAILED -> FeatureReader [INITIATOR]
Note: Reading QC CKAN-API
Catalogue_Reader: Catalogue Reader
    CUSTOM_CSW_LIST_NAME = DefaultNoList{}
    CUSTOM_URL = https://www.donneesquebec.ca/recherche/api/action
    SOURCE_URL = Manuel
    Résultats -> ATTRIBUTE_VALUE_TEXT_CLEANER
Note: Read CKAN data strored in the FFS file
FeatureReader
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> ATTRIBUTE_VALUE_TEXT_CLEANER

Bookmark: attribute
Note: Basic cleaning of the different attributes
ATTRIBUTE_VALUE_TEXT_CLEANER
    -> AttributeExposer_3
AttributeExposer_3
    ATTR_TABLE = license_id,
    -> LICENSE_FILTER_NG
Note: Filter the records accordint to the type of license
LICENSE_FILTER_NG
    FEATURE_TYPE = License_QC
    IN_CSV_LOOKUP_TABLES_DIR = $(IN_CSV_LOOKUP_TABLES_DIR)
    LICENSE_ATT = @Value(license_id)
    P-T_ABBR = QC
    LICENSE_FILTER_PASSED -> AttributeExposer_17
    UNKNOWN_LICENSE -> UNKNOWN_LICENCE (writer XLSXW_1)
Note: Exposes attributes required by this transformer
AttributeExposer_17
    ATTR_TABLE = metadata_created,,metadata_modified,,temporal,
    -> DateTimeConverter_4
Note: Sets 'metadata_created' and 'metadata_modified' to ISO yyyy-mm-dd format
DateTimeConverter_4
    DATETIME_ATTR = metadata_created metadata_modified
    OUT_FORMAT = %Y-%m-%d
    PASSTHROUGH = NO
    REPAIR_INPUT = YES
    -> AttributeCopier
Note: Copies 'metadata_created' attribute to 'record_create_date' and 'record_publish_date' attributes, and copies 'metadata_modiied' attribute to 'record_last_modified' attribute
AttributeCopier
    ATTR_TABLE:
      COPY metadata_created > record_create_date
      COPY metadata_created > record_publish_date
      COPY metadata_modified > record_last_modified
    MISSING_INPUT_ATTRS = PRESERVE
    -> EXTRACT_COLLECTION_START_END_DATE
EXTRACT_COLLECTION_START_END_DATE
    CSV_PATH = $(IN_CSV_LOOKUP_TABLES_DIR)
    DATE_EXTENT = @Value(temporal)
    FEATURE_TYPE = QC_Manual_end_start_collection_date
    PT = QC
    -> AttributeRemover
    Unworking_extent -> VariableRetriever_6
VariableRetriever_6
    SCOPE = Global
    VALUE_ATTR = _timestamp
    VARNAME = _timestamp
    -> AttributeExposer_16
AttributeExposer_16
    ATTR_TABLE = id,
    -> UNWORKING_DATE_COLLECTION_EXTENT (writer XLSXW_1)
UNWORKING_DATE_COLLECTION_EXTENT (writer XLSXW_1)
    attributes: unmatched_date_extent string(200), id string(200)
Note: Date Attribute cleanup
AttributeRemover
    REMOVE_ATTRS = metadata_created,temporal,metadata_modified
    -> DEFAULT_ATTRIBUTE_MAPPER_NG
UNKNOWN_LICENCE (writer XLSXW_1)
    attributes: license_id auto(20), id auto(20)

Bookmark: Default value
Note: Sets default attribute values
DEFAULT_ATTRIBUTE_MAPPER_NG
    FEATURE_TYPE = Default_QC
    IN_CSV_LOOKUP_TABLES_DIR = $(IN_CSV_LOOKUP_TABLES_DIR)
    P-T_ABBR = QC
    -> ATTRIBUTE_MANAGER_NG
ATTRIBUTE_MANAGER_NG
    IN_YAML_TEXT:
      author:
          action: attribute_not_null
          attr2set: organization.title

      update_frequency:
          action: attribute_not_null
          attr2set: default_update_frequency

      progress_code:
          action: attribute_overwrite
          attr2set: update_frequency

      contacts{0}.name:
         action: attribute_overwrite
         attr2set: author

      contacts{0}.email:
         action: attribute_overwrite
         attr2set: author_email

      sector:
          action: attribute_overwrite
          attr2set: organization.title

      location:
          action: attribute_overwrite
          attr2set: ext_spatial

      tags{0}.display_name:
          action: attribute_not_null
          attr2set: default_tag

      notes:
           action: attribute_not_null
           attr2set: title

      groups{}.name:
          action: attribute_not_null
          attr2set: default_topic_subject
    -> RESOURCES_VALIDATOR

Bookmark: Attribute Validation
Note: Validates url, name and format on resources{} list items
RESOURCES_VALIDATOR
    -> FORMAT_VALIDATOR
Note: Verfication if URL is valid WMS call for WMS formats
FORMAT_VALIDATOR
    -> AttributeExposer_6

Bookmark: Email format
AttributeExposer_6
    ATTR_TABLE = default_contact_email,
    -> EMAIL_FORMAT_TESTER
Note: Tests for and corrects missing '@' in email addresses and email separated by a comma delimiter
EMAIL_FORMAT_TESTER
    DEFAULT_CONTACT_EMAIL = @Value(default_contact_email)
    -> METADATA_VALUE_MAPPER_NG_8 [DATA_INPUT]
Note: Correction de valeur bizarre de courriel
METADATA_VALUE_MAPPER_NG_8
    ATT_TO_MAP = contacts{}.email
    CODE_REFRESH = NO
    ENGLISH_REFRESH = YES
    ERROR_NOT_MAPPED = NO
    FEATURE_TYPE = Email
    FRENCH_REFRESH = NO
    IN_CSV_LOOKUP_TABLES_DIR = $(IN_CSV_LOOKUP_TABLES_DIR)
    P-T_ABBR = $(P-T_ABBR)
    -> QC_MISSING_EMAIL_MAPPER

Bookmark: QC Missing eMail Mapper
Note: Add default_contact_email when contact email is missing
QC_MISSING_EMAIL_MAPPER: QC_MISSING_EMAIL_SETTER
    DATA_OUTPUT_PASSED -> AttributeExposer_8

Bookmark: Qdd QC Geoportal Weblink
AttributeExposer_8
    ATTR_TABLE = id,
    -> GEOPORTAL_WEBLINK_ADDER_NG
Note: Validate web link
GEOPORTAL_WEBLINK_ADDER_NG
    FEATURE_TYPE = GeoportalWeblink_QC
    IN_CSV_LOOKUP_TABLES_DIR = $(IN_CSV_LOOKUP_TABLES_DIR)
    P-T_ABBR = QC
    URL_VALIDATION = $(URL_VALIDATION)
    WEBLINK_WILDCARD = @Value(id)
    -> SECTOR_MAPPER_NG

Bookmark: Sector Mapper
SECTOR_MAPPER_NG
    FEATURE_TYPE = Sector_QC
    IN_CSV_LOOKUP_TABLES_DIR = $(IN_CSV_LOOKUP_TABLES_DIR)
    P-T_ABBR = QC
    PUBLISHED_OUTPUT -> GEO_NONE_GEO_SELECTOR
    UNMAPPED_OUTPUT -> SECTORS_NOT_MAPPED (writer XLSXW_1)
SECTORS_NOT_MAPPED (writer XLSXW_1)
    attributes: sector auto(20), id auto(20)

Bookmark: spatial data type management
Note: Differenciate Geo and None Geo records based on atrribute values and CV files
GEO_NONE_GEO_SELECTOR
    CSV_FILE_NAME = GeoSpatialValidation
    CSV_PATH = $(IN_CSV_LOOKUP_TABLES_DIR)
    CSV_PROVINCE = QC
    YAML_DIRECTIVES:
      resources{}.format:
        domain: lookup_table_format
        spatial_type: overwrite
        not_found: log
        search_type: equals
      #
      tags{}.display_name:
        domain: [Photographie aérienne,Toponyme,Toponymie,photogrammétrie,GPS,cartographie]
        spatial_type: no_overwrite
        not_found: no_log
        search_type: contains
    GEOSPATIAL -> SPATIAL_TYPE_MAPPER_NG [DATA_INPUT]
    NONE_GEOSPATIAL -> MANUAL_GEOSPATIAL_SETTER_NG [DATA_INPUT]
    LOG_ERROR -> GEOSPATIAL_FORMAT_NOT_MAPPED (writer XLSXW_1)
Note: Uses algorithm to determine spatial_representation_type of dataset
SPATIAL_TYPE_MAPPER_NG
    FEATURE_TYPE = UUID_Spatial_QC
    IN_CSV_LOOKUP_TABLES_DIR = $(IN_CSV_LOOKUP_TABLES_DIR)
    P-T_ABBR = QC
    DATA_OUTPUT_FAILED -> AttributeExposer_5
    DATA_OUTPUT_PASSED -> TestFilter_3
AttributeExposer_5
    ATTR_TABLE = id,,title,,notes,
    -> SPATIALTYPE_NOT_MAPPED (writer XLSXW_1)
SPATIALTYPE_NOT_MAPPED (writer XLSXW_1)
    attributes: notes auto(20), title auto(20), id auto(20)
MANUAL_GEOSPATIAL_SETTER_NG
    FEATURE_TYPE = UnmappedGeoData_QC
    IN_CSV_LOOKUP_TABLES_DIR = $(IN_CSV_LOOKUP_TABLES_DIR)
    P-T_ABBR = QC
    GEOSPATIAL -> TestFilter_3
    NON-GEOSPATIAL -> TestFilter_4
    UNMAPPED_DATA -> UNMAPPED_DATA (writer XLSXW_1)
Note: Test non sesible à la case
TestFilter_3
    DEFAULT_VALUE = <UNFILTERED>
    PASSED_TEST_GROUP_OUTPUT = FIRST
    TEST_LIST = "BOOL_OP,OR,COMPOSITE_TEST,""""""1"""""",TEST_CLAUSE,CASE_INSENSITIVE_TEST $(ACTIVATE_GEO) = yes",ACTIVATE_GEO
    ACTIVATE_GEO -> TestFilter
UNMAPPED_DATA (writer XLSXW_1)
    attributes: notes auto(20), title auto(20), id auto(20)
Note: Test non sesible à la case
TestFilter_4
    DEFAULT_VALUE = <UNFILTERED>
    PASSED_TEST_GROUP_OUTPUT = FIRST
    TEST_LIST = "BOOL_OP,OR,COMPOSITE_TEST,""""""1"""""",TEST_CLAUSE,CASE_INSENSITIVE_TEST $(ACTIVATE_NON_GEO) = yes",ACTIVATE_NON_GEO
    ACTIVATE_NON_GEO -> TestFilter_2
GEOSPATIAL_FORMAT_NOT_MAPPED (writer XLSXW_1)
    attributes: format string(8), id string(8)

Bookmark: Samples or full content
TestFilter
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_4
    SAMPLES FEATURES -> Sampler
Sampler
    MODE = ORIGINAL
    RATE = $(SAMPLE_SIZE)
    SAMPLE_TYPE_MULTIPLIER = -1
    SAMPLE_MODE = No
    SAMPLE_TYPE_LONG = First N Features
    SAMPLED -> Junction_4

Bookmark: Projection and GeoExtents Management
Note: Extracts projection values and bounding box coordinates from url, wms or esri rest, where they exist. Missing projection values are set to unknown
QC_PROJECTION_GEOEXTENTS_EXTRACTOR
    DATA_OUTPUT -> GEO_EXTENTS_MAPPER_NG
Note: Sets geoextents not created in previous transformer based on lookup table values
GEO_EXTENTS_MAPPER_NG
    FEATURE_TYPE = Coord_QC
    IN_CSV_LOOKUP_TABLES_DIR = $(IN_CSV_LOOKUP_TABLES_DIR)
    LATITUDE_MAX = 64
    LATITUDE_MIN = 44
    LONGITUDE_MAX = -56
    LONGITUDE_MIN = -80
    P-T_ABBR = QC
    EXTENT_DEFINED -> METADATA_VALUE_MAPPER_NG [DATA_INPUT]
    UNKNOWN_EXTENT -> GEO_EXTENTS_NOT_MAPPED (writer XLSXW_1)
GEO_EXTENTS_NOT_MAPPED (writer XLSXW_1)
    attributes: location string(20), id auto(20)

Bookmark: Attribute value mapper
Note: Maps update cycle to HNAP standards
METADATA_VALUE_MAPPER_NG
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUP_TABLES_DIR)
    P-T_ABBR = QC
    -> METADATA_VALUE_MAPPER_NG_2 [DATA_INPUT]
Note: Maps progress code to HNAP standards
METADATA_VALUE_MAPPER_NG_2
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUP_TABLES_DIR)
    P-T_ABBR = QC
    -> METADATA_VALUE_MAPPER_NG_3 [DATA_INPUT]
Note: Maps progress code to HNAP standards
METADATA_VALUE_MAPPER_NG_3
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUP_TABLES_DIR)
    P-T_ABBR = QC
    -> METADATA_FORMAT_MAPPER_NG [DATA_INPUT]
Note: Resources.format
METADATA_FORMAT_MAPPER_NG
    ATT_TO_MAP = resources{}.format
    ERROR_NOT_MAPPED = YES
    FEATURE_TYPE = Format
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_Geo (writer XLSXW_1)
    -> METADATA_VALUE_MAPPER_ERROR_MANAGER

Bookmark: Mapping error list creator
Note: Creates list of errors found and not corrected in mapping
METADATA_VALUE_MAPPER_ERROR_MANAGER
    ERROR_OUTPUT -> METADATA_MAPPING_ERRORS_GEO (writer XLSXW_1)
    DATA_OUTPUT -> URL_CHARACTER_ENCODER
METADATA_MAPPING_ERRORS_GEO (writer XLSXW_1)
    attributes: error string(200), id string(200)

Bookmark: URL Character Encoder
Note: URL's containing {} will not validate. UTF8 value is substituted where they exist.
URL_CHARACTER_ENCODER
    DATA_OUTPUT -> QC_WMS_URL_SETTER [DATA_INPUT]

Bookmark: Samples or full content
TestFilter_2
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction
    SAMPLES FEATURES -> Sampler_2
Sampler_2
    MODE = ORIGINAL
    RATE = $(SAMPLE_SIZE)
    SAMPLE_TYPE_MULTIPLIER = -1
    SAMPLE_MODE = No
    SAMPLE_TYPE_LONG = First N Features
    SAMPLED -> Junction

Bookmark: Non-geospatial processing
METADATA_VALUE_MAPPER_NG_4
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUP_TABLES_DIR)
    P-T_ABBR = QC
    -> AttributeExposer
AttributeExposer
    ATTR_TABLE = groups{}.name,
    -> ListCopier_2
ListCopier_2
    DEST_LIST = topics
    SRC_LIST = groups{}
    -> METADATA_VALUE_MAPPER_NG_5 [DATA_INPUT]
METADATA_VALUE_MAPPER_NG_5
    ATT_TO_MAP = topics{}.name
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUP_TABLES_DIR)
    P-T_ABBR = QC
    -> AttributeExposer_2
AttributeExposer_2
    ATTR_TABLE = topics{}.name,
    -> ListDuplicateRemover
ListDuplicateRemover
    SRC_LIST = topics{}.name
    -> AttributeExposer_10
AttributeExposer_10
    ATTR_TABLE = groups{}.name,
    -> ListCopier_3
ListCopier_3
    DEST_LIST = subjects
    SRC_LIST = groups{}
    -> METADATA_VALUE_MAPPER_NG_6 [DATA_INPUT]
METADATA_VALUE_MAPPER_NG_6
    ATT_TO_MAP = subjects{}.name
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUP_TABLES_DIR)
    P-T_ABBR = QC
    -> AttributeExposer_13
AttributeExposer_13
    ATTR_TABLE = subjects{}.name,
    -> ListDuplicateRemover_2
ListDuplicateRemover_2
    SRC_LIST = subjects{}.name
    -> METADATA_FORMAT_MAPPER_NG_2 [DATA_INPUT]
Note: Format
METADATA_FORMAT_MAPPER_NG_2
    ATT_TO_MAP = resources{}.format
    ERROR_NOT_MAPPED = YES
    FEATURE_TYPE = Format_TBS
    IN_CSV_LOOKUP_TABLES_DIR = $(IN_CSV_LOOKUP_TABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_NoneGeo (writer XLSXW_1)
    -> METADATA_VALUE_MAPPER_ERROR_MANAGER_2
Note: Creates list of errors found and not corrected in mapping
METADATA_VALUE_MAPPER_ERROR_MANAGER_2
    ERROR_OUTPUT -> METADATA_MAPPING_ERRORS_NON_GEO (writer XLSXW_1)
    DATA_OUTPUT -> AttributeExposer_18
AttributeExposer_18
    ATTR_TABLE = search_criteria_pycsw,,csw_url,,record_last_modified,,id,
    -> METADATA_DELTA_FINDER_GEN_2
METADATA_DELTA_FINDER_GEN_2
    ATTR_DATE_MODIFIED = record_last_modified
    LOCAL_SOURCE = Yes
    METADATA_OVERWRITE = $(METADATA_OVERWRITE)
    METADATA_TYPE = JSON-CKANExtCa
    SOURCE_DIRECTORY = $(OUT_JSON_LOCAL_DIR)
    VALIDATE_INSERT_PCT = $(VALIDATE_INSERT_PCT_JSON)
    YAML_FILE = $(IN_CSV_LOOKUP_TABLES_DIR)\$(P-T_ABBR)\metadata_delta_finder_$(P-T_ABBR)_non_geo.yaml
    Statistics -> StatisticsCalculator_Summary_3
    Update -> Junction_6
    Insert -> Junction_6
    Delete -> AttributeExposer_11
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
AttributeExposer_11
    ATTR_TABLE = id,,title,
    -> DELETED_RECORDS_NONE_GEO (writer XLSXW_1)
DELETED_RECORDS_NONE_GEO (writer XLSXW_1)
    attributes: id auto(20), title auto(20)
Junction_6
    -> AWS_TRANSLATE_2
Note: Translates specific items from French to English
AWS_TRANSLATE_2
    ACTIVATE_TRANSLATION = $(ACTIVATE_TRANSLATION)
    ATTR_2_TRANSLATE = notes,title
    ATTR_LIST_2_TRANSLATE = tags{}.display_name,resources{}.name
    MODE = French-->English
    -> JSON_PUBLISHER_NG
    TRANSLATION_PROBLEM -> AttributeExposer_12
JSON_PUBLISHER_NG
    FEATURE_TYPE = JSON_CONFIG_QC
    IN_CSV_LOOKUP_TABLES_DIR = $(IN_CSV_LOOKUP_TABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.display_name_en
    Keywords_FR = tags{}.display_name
    P-T_ABBR = $(P-T_ABBR)
    Subject_LIST = subjects{}.name
    Topic_LIST = topics{}.name
    OUTPUT_LOCAL -> AttributeExposer_4
AttributeExposer_4
    ATTR_TABLE = json_file,,id,
    -> AttributeCreator_6
AttributeCreator_6
    ATTR_TABLE = SET_TO text_line_data (varchar(200)) = @Value(json_file)
    -> text_line (writer TEXTLINE_4)
text_line (writer TEXTLINE_4)
    attributes: text_line_data buffer
AttributeExposer_12
    ATTR_TABLE = id,,title,
    -> TRANSLATION_PROBLEMS_NONE_GEO (writer XLSXW_1)
TRANSLATION_PROBLEMS_NONE_GEO (writer XLSXW_1)
    attributes: id auto(20), title auto(20)
METADATA_MAPPING_ERRORS_NON_GEO (writer XLSXW_1)
    attributes: error string(200), id string(200), _element_index string(200)

Bookmark: QC_WMS_URL_SETTER
LOOKUP_TABLES_READER_NG
    CSV_ENCODING = utf-8
    CSV_PATH = $(IN_CSV_LOOKUP_TABLES_DIR)
    FEATURE_TYPE = WMS_URL_QC
    PT = QC
    -> QC_WMS_URL_SETTER [LOOKUP_TABLE_INPUT]
QC_WMS_URL_SETTER
    -> REMOVE_BROKEN_URL_WMS_ESRI_REST

Bookmark: Data cleanup. Dropping broken web services
Note: Tests WMS/ESRI_REST resource URL's and removes them where broken
REMOVE_BROKEN_URL_WMS_ESRI_REST
    URL_VALIDATION = Yes
    -> WMS_REST_LANGUAGE_FORMATTER
    FAULTY_URL_OUTPUT -> MAP_SERVICE_URL_ERROR (writer XLSXW_1)
MAP_SERVICE_URL_ERROR (writer XLSXW_1)
    attributes: id auto(20), format string(8), url auto(20), _url_failure_message auto(20)

Bookmark: HNAP Rules- 1 web service per language.
Note: Formats WMS and ESRI REST resources to add French versions and formats French and English versions with valid supporting attributes
WMS_REST_LANGUAGE_FORMATTER
    -> DUPLICATE_SERVICE_REMOVER
Note: Removes duplicate WMS or ESRI REST resources where they exist, that would otherwise invalidate the dataset
DUPLICATE_SERVICE_REMOVER
    -> RESOURCE_NAME_UNDERSCORE_REMOVER

Bookmark: Data preparation for metadata section
Note: Removes all underscores from resources{}.name attributes. Long compounded names joined by underscores in this field can cause display formatting issues when published to the FGP.
RESOURCE_NAME_UNDERSCORE_REMOVER
    DATA_OUTPUT -> AttributeExposer_9
AttributeExposer_9
    ATTR_TABLE = resources{},
    -> ListCopier
ListCopier
    DEST_LIST = distributionList
    SRC_LIST = resources{}
    -> GMD_SECTION_DATA_EXTRACTION
Note: Creates lists and removes duplicates for GMD_Section
GMD_SECTION_DATA_EXTRACTION
    -> MORE_INFO_MANAGER
Note: Tests the more_info{}.link list for valid attribute values and filters them out where missing
MORE_INFO_MANAGER
    -> MAP_RESOURCE_ATTRIBUTION_REMOVER_NG
MAP_RESOURCE_ATTRIBUTION_REMOVER_NG
    FEATURE_TYPE = MAP_RES_REMOVE_QC
    IN_CSV_LOOKUP_TABLES_DIR = $(IN_CSV_LOOKUP_TABLES_DIR)
    P-T_ABBR = QC
    -> PythonCaller

Bookmark: Pregenrate formating for ressources description
PythonCaller
    NEW_ATTRIBUTES = resources{}.description_temp buffer
    PYTHONSOURCE:
      import fme
      import fmeobjects
      # Template Function interface:
      # When using this function, make sure its name is set as the value of
      # the 'Class or Function to Process Features' transformer parameter
      def processFeature(feature):
          lang=feature.getAttribute('transfer_option_description_language')

          for i in range(len(feature.getAttribute('resources{}.url'))):
              format=feature.getAttribute('resources{%i}.format'%(i))
              restype=feature.getAttribute('resources{%i}.format_resourceType_en'%(i))

              feature.setAttribute('resources{%i}.description_temp'%(i),'%s;%s;%s'%(restype,format,lang))
    PYTHONSYMBOL = processFeature
    -> AttributeCreator

Bookmark: Configuring publishing info
AttributeCreator
    ATTR_TABLE = SET_TO csw_url (varchar(200)) = $(FORCED_PYCSW_URL)
    -> ATTRIBUTE_MANAGER_NG_7
AttributeExposer_32
    ATTR_TABLE = search_criteria_pycsw,,csw_url,,record_last_modified,,id,
    -> METADATA_DELTA_FINDER_GEN
METADATA_DELTA_FINDER_GEN
    ATTR_DATE_MODIFIED = record_last_modified
    CSW_FILTER = @Value(search_criteria_pycsw)
    LOCAL_SOURCE = $(LOCAL_SOURCE_METADATA_DELTA_FINDER)
    METADATA_OVERWRITE = $(METADATA_OVERWRITE)
    METADATA_TYPE = XML-HNAP
    SOURCE_DIRECTORY = $(OUT_XML_LOCAL_DIR)
    SOURCE_URL = @Value(csw_url)
    VALIDATE_INSERT_PCT = $(VALIDATE_INSERT_PCT_XML)
    YAML_FILE = $(IN_CSV_LOOKUP_TABLES_DIR)\$(P-T_ABBR)\metadata_delta_finder_$(P-T_ABBR)_geo.yaml
    Statistics -> StatisticsCalculator_Summary_2
    Update -> Junction_5
    Insert -> Junction_5
    Delete -> AttributeExposer_15
StatisticsCalculator_Summary_2: Logger
    LOG_FEATURE = NONE
    MAXFEATS = 20
    MESSAGE:
      ************************
      **** Geo Features: Unchanged Report ****
      ************************

      @Value(_real_count) features were unchanged

      ************************
      ************************
      ************************
    SEVERITY = INFO
AttributeExposer_15
    ATTR_TABLE = id,,title,
    -> DELETED_RECORDS_GEO (writer XLSXW_1)
DELETED_RECORDS_GEO (writer XLSXW_1)
    attributes: id auto(20), title auto(20)
Junction_5
    -> AWS_TRANSLATE

Bookmark: Listes Metadata_delta_finder
ATTRIBUTE_MANAGER_NG_7
    IN_YAML_TEXT:
      distributionList{0}.format_version:
         action: attribute_not_null
         attr2set: distribution_format_version
      resources{0}.language:
         action: attribute_not_null
         attr2set: transfer_option_description_language
      contacts{0}.p-t_entity:
         action: attribute_not_null
         attr2set: p-t_entity_en
      contacts{0}.organization.title:
         action: attribute_not_null
         attr2set: sector
      contacts{0}.p-t_entity_fr:
         action: attribute_not_null
         attr2set: p-t_entity_fr
      iso_topic{0}.topic_value:
         action: attribute_not_null
         attr2set: iso_topic
    -> ATTRIBUTE_MANAGER_NG_8
ATTRIBUTE_MANAGER_NG_8
    IN_YAML_TEXT:
      distributionList{}.format_version:
         action: attribute_not_null
         attr2set: distribution_format_version
      resources{}.language:
         action: attribute_not_null
         attr2set: transfer_option_description_language
      contacts{}.p-t_entity:
         action: attribute_not_null
         attr2set: p-t_entity_en
      contacts{}.organization.title:
         action: attribute_not_null
         attr2set: sector
      contacts{}.p-t_entity_fr:
         action: attribute_not_null
         attr2set: p-t_entity_fr
      iso_topic{}.topic_value:
         action: attribute_not_null
         attr2set: iso_topic
    -> AttributeExposer_32

Bookmark: Language Translation
Note: Translates specific items from French to English
AWS_TRANSLATE
    ACTIVATE_TRANSLATION = $(ACTIVATE_TRANSLATION)
    ATTR_2_TRANSLATE = notes,title
    ATTR_LIST_2_TRANSLATE = tags{}.display_name,resources{}.name
    MODE = French-->English
    -> XML_PUBLISHER_NG
    TRANSLATION_PROBLEM -> AttributeExposer_14
AttributeExposer_14
    ATTR_TABLE = id,,title,
    -> TRANSLATION_PROBLEMS_GEO (writer XLSXW_1)
TRANSLATION_PROBLEMS_GEO (writer XLSXW_1)
    attributes: id auto(20), title auto(20)

Bookmark: XML CREATION AND WRITING
Note: CSV config file to map QC attributes to those required by XML templates
XML_PUBLISHER_NG
    FEATURE_TYPE = Config_QC
    IN_CSV_LOOKUP_TABLES_DIR = $(IN_CSV_LOOKUP_TABLES_DIR)
    LOCAL_WRITER = $(LOCAL_WRITER)
    P-T_ABBR = $(P-T_ABBR)
    TEMPLATE_GMD_CITEDRESPONSIBLEPARTY = $(IN_GMD_XML_TEMPLATE_DIR)\GMD_CITEDRESPONSIBLEPARTY.xml
    TEMPLATE_GMD_CONTACT = $(IN_GMD_XML_TEMPLATE_DIR)\GMD_CONTACT.xml
    TEMPLATE_GMD_DISTRIBUTIONFORMAT = $(IN_GMD_XML_TEMPLATE_DIR)\GMD_DISTRIBUTIONFORMAT.xml
    TEMPLATE_GMD_DISTRIBUTOR = $(IN_GMD_XML_TEMPLATE_DIR)\GMD_DISTRIBUTOR.xml
    TEMPLATE_GMD_KEYWORDS = $(IN_GMD_XML_TEMPLATE_DIR)\GMD_KEYWORDS.xml
    TEMPLATE_GMD_MDMETADATA = $(IN_GMD_XML_TEMPLATE_DIR)\GMD_MDMETADATA.xml
    TEMPLATE_GMD_REFERENCESYSTEMINFO = $(IN_GMD_XML_TEMPLATE_DIR)\GMD_REFERENCESYSTEMINFO.xml
    TEMPLATE_GMD_RESOURCEMAINTENANCE = $(IN_GMD_XML_TEMPLATE_DIR)\GMD_RESOURCEMAINTENANCE.xml
    TEMPLATE_GMD_TOPICCATEGORY = $(IN_GMD_XML_TEMPLATE_DIR)\GMD_TOPICCATEGORY.xml
    TEMPLATE_GMD_TRANSFEROPTIONS = $(IN_GMD_XML_TEMPLATE_DIR)\GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> INVALID_METADATA_PUBLISHER (writer XLSXW_1)
    UPDATE_FAILED -> text_line (writer TEXTLINE_2)
Note: Extracts and maps attributes to values required by the XML root template or sub-templates, compliles the templates to a single XML file, and publishes the XML to the PyCSW, or to a local folder. / NOTE: The publication method is defaulted to 'Auto', which will default the publication method to 'Insert'. Can override to 'Local', 'Insert' or 'Update' by selecting option in pubished parameter 'METHOD_SELECT'.
INVALID_METADATA_PUBLISHER (writer XLSXW_1)
    attributes: id auto(20)

FME custom transformer MAP_RESOURCE_ATTRIBUTION_REMOVER
Description 
This transformer tests if the ressources{}.url from the metadata records are present in the lookup table, if yes then it sets the xlink_role and protocol attributes
Input Ports 
URL: URL from the lookup table.
INPUT: Input metadata records to process.
Output Ports 
OUTPUT: The process output metdata records.
Parameters 
NONE

URL (input)
    -> AttributeExposer_2
AttributeExposer_2
    ATTR_LIST = url
    -> AttributeCreator
Note: Sorting order
AttributeCreator
    ATTR_TABLE = SET_TO _type = A
    -> Sorter
Input (input)
    -> AttributeExposer
AttributeExposer
    ATTR_LIST = resources{}.url
    -> ListElementCounter
Note: Count number of ressources{} occurrences
ListElementCounter
    CNT_ATTR = _element_count
    LIST_NAME = resources{}
    -> AttributeCreator_2
Note: Sorting order
AttributeCreator_2
    ATTR_TABLE = SET_TO _type = B
    -> Sorter
Note: Sort lookup table entry firstly. Metadata records secondly.
Sorter
    SORT_PARM = _type ALPHA ASCENDING
    SORTED -> PythonCaller
Note: Check if URL from the ressources{}.url is present in the looup table and set some attributes
PythonCaller
    PYTHONSOURCE:
      import fme
      import fmeobjects
      # Template Function interface:
      # When using this function, make sure its name is set as the value of
      # the 'Class or Function to Process Features' transformer parameter

      class FeatureProcessor(object):
          def __init__(self):
              self.url=[]

          def input(self,feature):
              # If the url of the ressources is present in the lookup table set some attributes

              if feature.getAttribute('_type')=='A':
                  #Adding URL from the llokup tablein the list
                  self.url.append(feature.getAttribute('url'))

              else:

                  if int(feature.getAttribute('_element_count'))>0:
                      for i in range(int(feature.getAttribute('_element_count'))):
                          url=feature.getAttribute('resources{%d}.url'%(i))
                          if url in self.url:
                              feature.setAttribute('resources{%d}.xlink_role'%(i),'')
                              feature.setAttribute('resources{%d}.protocol'%(i),'HTTPS')

                  # Release the feature
                  self.pyoutput(feature)

          def close(self):
              pass
    PYTHONSYMBOL = FeatureProcessor
    -> ATTRIBUTE_UNEXPOSER
ATTRIBUTE_UNEXPOSER
    -> Output (output)
Output (output)

FME custom transformer GEOSPATIAL_DATA_VALIDATOR
Description 
This custom transformer fan out the metadata records between three types of metadata (GeoSpatial, Non GeoSpatial and Unknown).  In order to determine the type of metadta record, the transformer is using two strategies: firstly by checking if the format has been published in the FGP (if positive it is a GeoSpatial record); secondly by checking the content of a list of keywords againts the content of an attribute in the metadata record (if there is a match it is a GeoSpatial record) 
Input Ports 
LOOKUP_TABLE_INPUT: Input information from the lookup table
DATA_INPUT: The input metadata records to process.
Output Ports 
GEOSPATIAL: Output port for all gepspatial metadata record
NON-GEOSPATIAL: Output port for all non geospatial metadata record
UNKNOWN_FORMAT: Output port for metadata record that cannot be mapped to geospatial or non geospatial
Parameters 
KEYWORD_SEARCH: List of keywords used to determine if a metadata record is geospatial.  If more than one keyword is needed, separate each keyword with a vertical bar "|"
LIST_SEARCH_ATTRIBITE: Name of the attribute in plain text (ex.: tag{}.display_name) used to search for a string match from the KEYWORD_SEARCH parameter

Parameters:
- KEYWORD_SEARCH =
- LIST_SEARCH_ATTRIBUTE =

LOOKUP_TABLE_INPUT (input)
    -> AttributeExposer_2
INPUT (input)
    -> AttributeExposer
UNKNOWN_FORMAT (output)
GEOSPATIAL (output)
NON-GEOSPATIAL (output)

Bookmark: Excel file validation
Note: Exposes attributes from lookup table
AttributeExposer_2
    ATTR_LIST = fgp_publish,format,spatial_type
    -> Tester_2
Note: Tests for value in required fields
Tester_2
    BOOL_OP = OR
    TEST_CLAUSE:
      TEST fgp_publish ATTRIBUTE_HAS_A_VALUE ""
      TEST format ATTRIBUTE_HAS_A_VALUE ""
    TEST_MODE = TEST
    PASSED -> DuplicateFilter
    FAILED -> Terminator
Terminator
    MESSAGE = Missing values in fgp_publish or format attributes, Geospatial lookup table, GEOSPATIAL_DATA_VALIDATOR transformer.  Translation terminated.
Note: Tests for duplicates of 'format' attribute
DuplicateFilter
    INPUT_ORDERED_CHOICE_LOOKUP = NO
    KEYATTR = format
    PRESERVE_FEATURE_ORDER_LOOKUP = PER_OUTPUT_PORT
    INPUT_ORDERED_CHOICE = No
    UNIQUE -> Tester
    DUPLICATE -> Terminator_2
Terminator_2
    MESSAGE = Duplicate feature @Value(format) found in format attribute in Geospatial lookup table, GEOSPATIAL_DATA_VALIDATOR transformer.  Translation terminated.
Note: Validates 'spatial_type' attribute format.
Tester
    BOOL_OP = OR
    TEST_CLAUSE:
      TEST @Value(spatial_type) = a-grid
      TEST @Value(spatial_type) = b-vector
      TEST @Value(spatial_type) = c-textTable
      TEST spatial_type NOT_ATTRIBUTE_HAS_A_VALUE ""
    TEST_MODE = TEST
    PASSED -> StringCaseChanger_2
    FAILED -> Terminator_3
Terminator_3
    MESSAGE = spatial_type attribute value @Value(spatial_type) from Geospatial lookup table is invalid in GEOSPATIAL_DATA_VALIDATOR transformer.  Value must be 'a-grid', 'b-vector','c-textTable' or value must be empty.  Translation terminated.
Note: Putting format and fgp_publish in lower case
StringCaseChanger_2
    ATTRCHOICE_ACTION = SELECTED
    ATTRLIST = fgp_publish format
    CHANGE_TYPE_CASE = lower
    ATTRCHOICE = Selected Attributes
    CHANGE_TYPE = lowercase
    -> FeatureMerger [SUPPLIER]

Bookmark: Geospatial Data Validator
Note: Exposes attributes from incoming data
AttributeExposer
    ATTR_LIST = resources{}.format,tags{}.display_name,id,resources{}.url,resources{}.name,notes,title,resources{}.fgp_publish
    -> UUIDGenerator
Note: Creates unique ID for rejoining data
UUIDGenerator
    UUID_ATTR = _uuid
    -> AttributeRenamer
    -> ListElementCounter
Note: Rename 'id' to 'original_id' as not to conflict with resources{}.id when resources{} list is exploded
AttributeRenamer
    ATTR_TABLE = RENAME_SET_DEFAULT id > orig_id
    -> AttributeKeeper
Note: Retains _uuid, original_id and resources{} list only
AttributeKeeper
    CREATE_BULK_MODE_FEATURES = No
    KEEP_ATTRS = notes,title,orig_id,_uuid
    KEEP_LIST = resources{}
    -> ListExploder
Note: Explodes resources{} list
ListExploder
    ATTR_CONFLICT_RES_LOOKUP = INCOMING_IF_CONFLICT
    INDEX_ATTR = _element_index
    LIST_ATTR = resources{}
    ATTR_ACCUM_MODE = Merge List Attributes
    ATTR_CONFLICT_RES = Use List Attribute Values
    ELEMENTS -> Tester_3
    <REJECTED> -> Cloner
Tester_3
    BOOL_OP = OR
    TEST_CLAUSE = TEST @LowerCase(@Value(fgp_publish)) = oui
    TEST_MODE = TEST
    PASSED -> StringCaseChanger
    FAILED -> AttributeRemover_3
AttributeRemover_3
    REMOVE_ATTRS = fgp_publish
    -> StringCaseChanger
Note: Putting format in lowercasse
StringCaseChanger
    ATTRCHOICE_ACTION = SELECTED
    ATTRLIST = format
    CHANGE_TYPE_CASE = lower
    ATTRCHOICE = Selected Attributes
    CHANGE_TYPE = lowercase
    -> FeatureMerger [REQUESTOR]
Note: Joins lookup table and feature data on value 'format'
FeatureMerger
    ATTR_CONFLICT_RES_LOOKUP = REQUESTOR_IF_CONFLICT
    IGNORE_NULLS = No
    JOIN_KEYS = @Value(format) @Value(format) AUTO
    MERGE_TYPE_VAL = ATTRIBUTES
    PROCESS_DUPS = NO
    REJECT_NULL_MISSING_KEYS = No
    SUPPLIERS_FIRST = No
    ATTR_ACCUM_MODE = Merge Supplier
    ATTR_CONFLICT_RES = Use Requestor
    MERGE_TYPE = Attributes Only
    MERGED -> FeatureMerger_2 [SUPPLIER]
    UNMERGED_REQUESTOR -> AttributeRenamer_2
    <REJECTED> -> Terminator_4
Terminator_4
    MESSAGE = Process failed at Feature Merger, GEOSPATIAL_DATA_VALIDATOR transformer.  Translation terminated.
Note: Rename 'orignal_id' back to 'id'
AttributeRenamer_2
    ATTR_TABLE = RENAME_SET_DEFAULT orig_id > id
    -> Logger
Logger
    LOG_FEATURE = LOG_ONLY
    MAXCOORDS = 20
    MAXFEATS = 20
    MESSAGE = Attribute value @Value(format) missing from Geospatial lookup table in GEOSPATIAL_DATA_VALIDATOR transformer.  See PROCESS_REPORT_MANUAL_TASKS.xls file in XLS directory for details.
    SEVERITY = WARN
    LOGGED -> AttributeKeeper_2
Note: Retains 'id' and 'format' for unmapped output file
AttributeKeeper_2
    CREATE_BULK_MODE_FEATURES = No
    KEEP_ATTRS = id,format
    -> UNKNOWN_FORMAT (output)
Cloner
    COPIES = 1
    COPYATT = _copynum
Note: Compter le nombre de ressource avec la vaidation
ListElementCounter
    CNT_ATTR = _nb_res_avant
    LIST_NAME = resources{}
    -> AttributeRemover
Note: Removes resources{} list
AttributeRemover
    LIST_ATTRS = resources{}
    -> FeatureMerger_2 [REQUESTOR]
Note: Rejoins data on _uuid attribute and rebuilds resources{} list
FeatureMerger_2
    ATTR_CONFLICT_RES_LOOKUP = REQUESTOR_IF_CONFLICT
    IGNORE_NULLS = No
    JOIN_KEYS = @Value(_uuid) @Value(_uuid) AUTO
    LIST_NAME = resources
    MERGE_TYPE_VAL = ATTRIBUTES
    PROCESS_DUPS = NO
    REJECT_NULL_MISSING_KEYS = No
    SUPPLIERS_FIRST = No
    ATTR_ACCUM_MODE = Merge Supplier
    ATTR_CONFLICT_RES = Use Requestor
    MERGE_TYPE = Attributes Only
    MERGED -> ListElementCounter_2
    <REJECTED> -> Terminator_5
ListElementCounter_2
    CNT_ATTR = _nb_res_apres
    LIST_NAME = resources{}
    -> Tester_4
Note: Uniquement les entités ayant le même nombre de ressource avant/apres / Si le nombre change, cela indique que des formats sont inconnus
Tester_4
    BOOL_OP = OR
    TEST_CLAUSE = TEST @Value(_nb_res_avant) = @Value(_nb_res_apres)
    TEST_MODE = TEST
    PASSED -> ListSearcher_2
Note: Searches resources{}.fgp_publish list for value 'Oui' for publishing
ListSearcher_2
    ATTR_VALUE = oui
    INDEX_ATTR = _list_index
    LIST_ATTR = resources{}.fgp_publish
    MATCHTYPE = REGULAR_EXPRESSION_ENCODED
    FOUND -> AttributeRemover_4
    NOT_FOUND -> ListSearcher
Note: Secondary list search. Searches on tags{}.display_name for BC and QC data and resources{}.contains_geographic_markers for ON data. LIST_SEARCH_ATTRIBUTE is the list attribute to be searched, KEYWORD_SEARCH represents the value(s).
ListSearcher
    ATTR_VALUE = $(KEYWORD_SEARCH)
    INDEX_ATTR = _list_index
    LIST_ATTR = $(LIST_SEARCH_ATTRIBUTE)
    MATCHTYPE = REGULAR_EXPRESSION_ENCODED
    FOUND -> AttributeRemover_4
    NOT_FOUND -> AttributeRemover_2
Note: Attribute cleanup
AttributeRemover_4
    LIST_ATTRS = resources{}._element_index resources{}._uuid resources{}.fgp_publish
    REMOVE_ATTRS = _element_index,format,_list_index,fgp_publish,_uuid
    -> ATTRIBUTE_UNEXPOSER
ATTRIBUTE_UNEXPOSER
    -> GEOSPATIAL (output)
Note: Attribute cleanup
AttributeRemover_2
    LIST_ATTRS = resources{}._element_index resources{}._uuid resources{}.fgp_publish
    REMOVE_ATTRS = _uuid,_element_index,format,fgp_publish
    -> ATTRIBUTE_UNEXPOSER_2
ATTRIBUTE_UNEXPOSER_2
    -> NON-GEOSPATIAL (output)
Terminator_5
    MESSAGE = Process failed at Feature Merger_2, GEOSPATIAL_DATA_VALIDATOR transformer.  Translation terminated.
