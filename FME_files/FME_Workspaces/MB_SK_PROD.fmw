FME workspace MB_SK_PROD.fmw
Title: MB_SK_PROD
Description: Description 
This workbench read and trasform all the metadata for the provinces of Manitoba (MB) and Saskatchewan (SK).
Input Ports 
None
Output Ports 
None
Parameters 
ACTIVATE_GEO: Flag enabling the processing of the geospatial features. Can take two values: Yes: Process the geospatial features; No: Do not process the geospatial features.
ACTIVATE_NON_GEO: Flag enabling the processing of the none geospatial features. Can take two values: Yes: Process the none geospatial features; No: Do not process the none geospatial features.
ACTIVATE_TRANSLATION: Flag enabling the translation of the texts using AWS service. Can take two values: Yes: Translates the texts; No: Do not translate the texts.  The Yes flag can only be used in production mode.
DCAT_READER_SELECT: Flag enabling the reading of the metadata from the P/T web service. Can take two values: Yes: Read the metadata from the P/T web service; No: Read the metadata from a local source on disk.
FORCED_PYCSW_URL: URL address of the PYCSW server used to update the metadata.
IN_FFS_TESTING_FILE: Name of a FFS file containing the metadata records read from the DCAT_READER. This file is used when the parameter: DCAT_READER_SELECT is set to No.
LOCAL_SOURCE_METADATA_DELTA_FINDER: Flag enabling the use of a local source for the metadata delta finder. Can take two values: Yes: Use a local source as defined by the parameter OUT_XML_LOCAL_DIR; No: use the content PyCSW server as defined by the parameter: FORCED_PYCSW_URL.
LOCAL_WRITER: Flag enabling to write the output locally or on the server.  Can take two values: Yes: Write the output locally as defined by the parameter:OUT_XML_LOCAL_DIR; No: Write the output in the PyCSW server as defined by the parameter: FORCEDS_PYCSW_URL.
P-T_ABBR: SK or MB
METADATA_OVERWRITE: Enable the overwite of the PyCSW.  Can take two values: Yes: Overwrite the contentof the PyCSW; No: Do no overwrite the content of the PyCSW.
IN_OUT_WORKING_DIR: Root working directory used to define the following private parameters:
IN_CSV_LOOKUP_TABLES_DIR: Source directory of the root of the lookup table files. Defined as: \LOOKUP_TABLES
IN_GMD_XML_TEMPLATES_DIR: Source directory of the root XML templates. Defined as: \XML_TEMPLATES
INJSON_TEMPLATE_DIR: Source directory of the root JSON templates. Defined as: \JSON_TEMPLATES
LOG_FILE: Output log file. Defined as: C:\Data\PT_Harvester\QC\LOG\QC.log
OUT_JSON_LOCAL_DIR: Source directory to output JSON files. Defined as: C:\Data\PT_Harvester\QC\JSON_LOCAL
OUT_XLS_NOTIFICATION: Source directory to output excel files. Defined as: C:\Data\PT_Harvester\QC\XLS
OUT_XML_FAILED_DIR: Source directory to output failed XML files. Defined as: C:\Data\PT_Harvester\QC\XML_FAILED
OUT_XML_LOCAL_DIR: Source directory to output Local Source XML files. Defined as: C:\Data\PT_Harvester\QC\XML_LOCAL
OUT_XML_PASSED_DIR: Source directory to output passedXML files. Defined as: C:\Data\PT_Harvester\QC\XML_PASSED
URL_VALIDATION : Indicates to validate or not created URL. (Should be Yes for prod)
VALIDATE_INSERT_PCT :Indicates to valide insert percentage. 75 % or less insert/update record  (Should be Yes for prod)

Parameters:
- ACTIVATE_GEO = Yes
- ACTIVATE_NON_GEO = Yes
- ACTIVATE_TRANSLATION = Yes
- CATALOGUE_READER_SELECT = Yes
- FORCED_PYCSW_URL =
- IN_FFS_TESTING_FILE =
- LOCAL_SOURCE_METADATA_DELTA_FINDER = No
- LOCAL_WRITER = No
- P-T_ABBR = SK
- METADATA_OVERWRITE = NO   # METADATA OVERWRITE
- IN_OUT_WORKING_DIR = $(FME_SHAREDRESOURCE_DATA)\PT_Harvester
- SAMPLE_SIZE = 0
- URL_VALIDATION = Yes
- VALIDATE_INSERT_PCT_JSON = Yes
- VALIDATE_INSERT_PCT_XML = Yes
- FME_USER_PARAM_PRIVATE_GRP =   # Private Parameters
- IN_CSV_LOOKUPTABLES_DIR = $(IN_OUT_WORKING_DIR)\LOOKUP_TABLES   # Lookup Tables Directory
- IN_GMD_XML_TEMPLATE_DIR = $(IN_OUT_WORKING_DIR)\XML_TEMPLATES
- IN_TBS_JSON_TEMPLATE_DIR = $(IN_OUT_WORKING_DIR)\JSON_TEMPLATES
- LOG_FILE = $(IN_OUT_WORKING_DIR)\$(P-T_ABBR)\LOG\$(P-T_ABBR).log
- OUT_JSON_LOCAL_DIR = $(IN_OUT_WORKING_DIR)\$(P-T_ABBR)\JSON_LOCAL
- OUT_XLS_NOTIFICATION_DIR = $(IN_OUT_WORKING_DIR)\$(P-T_ABBR)\XLS
- OUT_XML_FAILED_DIR = $(IN_OUT_WORKING_DIR)\$(P-T_ABBR)\XML_FAILED
- OUT_XML_LOCAL_DIR = $(IN_OUT_WORKING_DIR)\$(P-T_ABBR)\XML_LOCAL
- OUT_XML_PASSED_DIR = $(IN_OUT_WORKING_DIR)\$(P-T_ABBR)\XML_PASSED
- IN_CSV_LOOKUP_TABLES_DIR = $(IN_OUT_WORKING_DIR)\LOOKUP_TABLES
- FME_SHAREDRESOURCE_DATA = C:\Data   # FME Flow Data Directory

Writers:
- TEXTLINE_1: TEXTLINE to $(OUT_XML_PASSED_DIR)
- TEXTLINE_2: TEXTLINE to $(OUT_XML_FAILED_DIR)
- TEXTLINE_3: TEXTLINE to $(OUT_XML_LOCAL_DIR)
- XLSXW_1: XLSXW to $(IN_OUT_WORKING_DIR)
- TEXTLINE_4: TEXTLINE to $(OUT_JSON_LOCAL_DIR)

Note: Notes for MB/SK workspace: / 1) Some metadata/resources for MB are in french. However, there is no functionnal attribute regarding language so all metadata have the default value 'english' for language. / 2) There are attributes concerning spatial projection/reference system but they have enough wrong values so that a default value was defined for these attributes. / 3) In the province's original metadata url there are sometimes values provided for the update frequency attribute that are absent from the 2 sources/api used in this workspace. A 3rd source migth have these values (might be worth looking into in the future). / 4) There are some inconsistencies between metadata date attribute (record created, published, last modified) between the province's original metadata url and the 2 sources/api used in this workspace. However, the values provided in the province's original metadata url seems less reliable (same value for most metadata).
AttributeExposer_18
    ATTR_TABLE = id,,title,,notes,
    -> SPATIAL_TYPE_NOT_MAPPED (writer XLSXW_1)

Bookmark: DCAT metadata reader
Creator
    GEOMTYPE = Geometry Object
    NUM = 1
    CREATED -> Tester
Tester
    BOOL_OP = OR
    TEST_CLAUSE = CASE_INSENSITIVE_TEST $(CATALOGUE_READER_SELECT) = Yes
    TEST_MODE = CASE_INSENSITIVE_TEST
    PASSED -> DCAT_Reader_MB_SK
    FAILED -> FeatureReader [INITIATOR]
Note: Merge metadata from 2 sources/api for MB and SK
DCAT_Reader_MB_SK
    IN_CSV_LOOKUPTABLES_DIR = $(IN_OUT_WORKING_DIR)\LOOKUP_TABLES
    IN_OUT_WORKING_DIR = $(IN_OUT_WORKING_DIR)
    LUT_DCAT_S_duplicate_last = DCAT_S_duplicates_last
    LUT_duplicate_attributes = $(P-T_ABBR)_duplicate_attributes
    P-T_ABBR = $(P-T_ABBR)
    -> Junction_4
    metadata_value_to_validate -> METADATA_VALUES_TO_VALIDATE (writer XLSXW_1)
METADATA_VALUES_TO_VALIDATE (writer XLSXW_1)
    attributes: id string(200), title string(200), DCAT_S_merge_error string(200), _attr_name string(20), _attr_value string(20)
FeatureReader
    ATTR_ACCUM_MODE = Only Use Result
    CLIP_TO_ENVELOPE = NO
    COMBINE_GEOM = Use Result
    DATASET = $(IN_FFS_TESTING_FILE)
    FFS_USE_SEARCH_ENVELOPE = NO
    FORMAT = FFS
    INITIATOR_FIRST_OUTPUT = default
    INTERACT = NONE
    ORDER_RESULTS = No
    OUTPUT_ADD_SCHEMA_ATTRIBUTES = NO
    OUTPUT_FEATURES_DISPLAY = Schema and Data Features
    OUTPUT_USE_SCHEMA_CACHE = YES
    READER_BEHAVIOR = Constraint Parameters
    <OTHER> -> Junction_4
Junction_4
    -> AttributeExposer_17

Bookmark: Rename attributes
AttributeExposer_17
    ATTR_TABLE = DCAT_P_identifier,,DCAT_P_title,,DCAT_P_license,,DCAT_P_issued,,DCAT_P_modified,,DCAT_S_attributes.metadata.metadata.dataIdInfo.dataExt{0}.tempEle.TempExtent.exTemp.TM_Period.tmBegin,,DCAT_S_attributes.metadata.metadata.dataIdInfo.dataExt{0}.tempEle.TempExtent.exTemp.TM_Period.tmEnd,,DCAT_P_publisher.name,,DCAT_S_attributes.snippet,,DCAT_S_attributes.searchDescription,,DCAT_P_spatial,,DCAT_P_distribution{},,DCAT_P_contactPoint.hasEmail,,DCAT_P_landingPage,,DCAT_P_keyword{},,DCAT_S_attributes.categories{},,DCAT_S_attributes.metadata.metadata.Esri.CreaDate,,DCAT_S_attributes.metadata.metadata.mdDateSt,,DCAT_S_attributes.metadata.metadata.dataIdInfo.idPurp,,DCAT_S_attributes.metadata.metadata.dataIdInfo.idAbs,,DCAT_S_attributes.description,,DCAT_P_description,,DCAT_S_id,,DCAT_P_id_layer,,DCAT_S_attributes.metadata.metadata.dataIdInfo.idCredit,,DCAT_S_attributes.server.copyrightText,,DCAT_S_attributes.organization,
    -> NullAttributeMapper_2
NullAttributeMapper_2
    ATTRCHOICE_ACTION = SELECTED
    ATTRLIST = DCAT_S_attributes.metadata.metadata.dataIdInfo.idCredit DCAT_S_attributes.server.copyrightText
    NULL_TREATMENT_LU = SETNULL
    OTHER_VALUE = Null
    SOURCE_ATTR_VAL_LU = MISSINGATTR
    ATTRCHOICE = Selected Attributes
    NULL_TREATMENT = Null
    SOURCE_ATTR_VAL = "Missing (Selected Attributes Only)"
    -> TestFilter_6
AttributeRenamer_4
    ATTR_TABLE:
      RENAME_SET_DEFAULT DCAT_P_id_layer > id
      RENAME_SET_DEFAULT DCAT_P_issued > record_create_date
      RENAME_SET_DEFAULT DCAT_P_modified > record_last_modified2
      RENAME_SET_DEFAULT DCAT_S_attributes.metadata.metadata.dataIdInfo.dataExt{0}.tempEle.TempExtent.exTemp.TM_Period.tmBegin > data_collection_start_date
      RENAME_SET_DEFAULT DCAT_S_attributes.metadata.metadata.dataIdInfo.dataExt{0}.tempEle.TempExtent.exTemp.TM_Period.tmEnd > data_collection_end_date
      RENAME_SET_DEFAULT DCAT_P_license > license
      RENAME_SET_DEFAULT DCAT_P_title > title
      RENAME_SET_DEFAULT DCAT_P_contactPoint.hasEmail > contact_email
      RENAME_SET_DEFAULT DCAT_P_landingPage > landingPage
      RENAME_SET_DEFAULT DCAT_S_attributes.snippet > notes1
      RENAME_SET_DEFAULT DCAT_S_attributes.searchDescription > notes2
      RENAME_SET_DEFAULT DCAT_S_attributes.metadata.metadata.mdDateSt > record_last_modified
    KEEP_RENAMED_ONLY = no
    MISSING_INPUT_ATTRS = PRESERVE
    -> AttributeCopier
AttributeCopier
    ATTR_TABLE:
      COPY id > original_id
      COPY record_create_date > record_publish_date
    MISSING_INPUT_ATTRS = PRESERVE
    -> AttributeSplitter
Note: Removing unnecessary attributes
BulkAttributeRemover
    ATTR_EXP = DCAT_[P<pipe>S]_
    -> StringReplacer

Bookmark: Création du sector en fonction de la province et des valeurs
TestFilter_6
    DEFAULT_VALUE = <UNFILTERED>
    PASSED_TEST_GROUP_OUTPUT = FIRST
    TEST_LIST = "BOOL_OP,OR,COMPOSITE_TEST,""""""1"""""",TEST_CLAUSE,CASE_INSENSITIVE_TEST $(P-T_ABBR) = SK",SK,"BOOL_OP,OR,COMPOSITE_TEST,""""""1"""""",TEST_CLAUSE,CASE_INSENSITIVE_TEST $(P-T_ABBR) = MB",MB
    SK -> ListConcatenator
    MB -> AttributeCreator_7
    <UNFILTERED> -> Terminator_2
ListConcatenator
    DROP_EMPTY_PARTS = No
    LIST_ATTR = DCAT_P_keyword{}
    SEP = ,
    VAL_ATTR = _concatenated_keyword_org
    -> AttributeCreator_2
AttributeCreator_2
    ATTR_TABLE = SET_TO sector (varchar(200)) = FME_CONDITIONAL:DEFAULT_VALUE'Government of Saskatchewan'BOOL_OP;OR;COMPOSITE_TEST;1;TEST DCAT_S_attributes.server.copyrightText ATTRIBUTE_HAS_A_VALUE _FME_BLANK_STRING_'@Value(DCAT_S_attributes.server.copyrightText)'BOOL_OP;AND;COMPOSITE_TEST;1 AND 2;TEST DCAT_S_attributes.metadata.metadata.dataIdInfo.idCredit ATTRIBUTE_HAS_A_VALUE _FME_BLANK_STRING_;TEST @Value(DCAT_S_attributes.metadata.metadata.dataIdInfo.idCredit) != Government of Saskatchewan'@Value(DCAT_S_attributes.metadata.metadata.dataIdInfo.idCredit)'BOOL_OP;OR;COMPOSITE_TEST;1;CASE_INSENSITIVE_TEST @Value(_concatenated_keyword_org) CONTAINS Saskatchewan Geological Survey'Saskatchewan Geological Survey'FME_NUM_CONDITIONS4___
    -> AttributeRemover
AttributeRemover
    REMOVE_ATTRS = _concatenated_keyword_org
    -> AttributeRenamer_4
AttributeCreator_7
    ATTR_TABLE = SET_TO sector (varchar(200)) = FME_CONDITIONAL:DEFAULT_VALUE'@Value(DCAT_S_attributes.organization)'BOOL_OP;OR;COMPOSITE_TEST;1;TEST @Value(DCAT_P_publisher.name) != Government of Manitoba'@Value(DCAT_P_publisher.name)'FME_NUM_CONDITIONS2___
    -> AttributeRenamer_4
Terminator_2
    MESSAGE = Translation Terminated

Bookmark: spatial_extent
AttributeSplitter
    ATTR_NAME = DCAT_P_spatial
    DELIMITER = ,
    DROP_EMPTY_PARTS = NO
    LIST_NAME = spatial_extent
    TRIM_TYPE = BOTH
    -> AttributeRenamer_2
AttributeRenamer_2
    ATTR_TABLE:
      RENAME_SET_DEFAULT spatial_extent{0} > west_bound_longitude
      RENAME_SET_DEFAULT spatial_extent{1} > south_bound_latitude
      RENAME_SET_DEFAULT spatial_extent{2} > east_bound_longitude
      RENAME_SET_DEFAULT spatial_extent{3} > north_bound_latitude
    KEEP_RENAMED_ONLY = no
    MISSING_INPUT_ATTRS = PRESERVE
    -> PythonCaller_5

Bookmark: Rename lists attributes
Note: topics (iso.topic{}.topic_value)
PythonCaller_5
    PYTHONSOURCE:
      import fme
      import fmeobjects
      from Python.FME_utils import FME_utils

      # Template Function interface:
      # When using this function, make sure its name is set as the value of
      # the 'Class or Function to Process Features' transformer parameter
      def FeatureProcessor(feature):

          max_index=FME_utils.max_index_attribute_list(feature,'DCAT_S_attributes.categories{}')
          for j in range(max_index+1):
              feature.setAttribute('iso_topic{%i}.topic_value'%(j),feature.getAttribute('DCAT_S_attributes.categories{%i}'%(j)))
    PYTHONSYMBOL = FeatureProcessor
    -> PythonCaller_6
Note: keywords (tags{}.value)
PythonCaller_6
    PYTHONSOURCE:
      import fme
      import fmeobjects
      from Python.FME_utils import FME_utils

      # Template Function interface:
      # When using this function, make sure its name is set as the value of
      # the 'Class or Function to Process Features' transformer parameter
      def FeatureProcessor(feature):

          max_index=FME_utils.max_index_attribute_list(feature,'DCAT_P_keyword{}')
          for j in range(max_index+1):
              feature.setAttribute('tags{%i}.value'%(j),feature.getAttribute('DCAT_P_keyword{%i}'%(j)))
    PYTHONSYMBOL = FeatureProcessor
    -> PythonCaller_3
Note: resources{}
PythonCaller_3
    PYTHONSOURCE:
      import fme
      import fmeobjects
      from Python.FME_utils import FME_utils

      # Template Function interface:
      # When using this function, make sure its name is set as the value of
      # the 'Class or Function to Process Features' transformer parameter
      def FeatureProcessor(feature):

          max_index=FME_utils.max_index_attribute_list(feature,'DCAT_P_distribution{}')
          for j in range(max_index+1):
              feature.setAttribute('resources{%i}.format'%(j),feature.getAttribute('DCAT_P_distribution{%i}.format'%(j)))
              feature.setAttribute('resources{%i}.name'%(j),feature.getAttribute('DCAT_P_distribution{%i}.title'%(j)))
              feature.setAttribute('resources{%i}.url'%(j),feature.getAttribute('DCAT_P_distribution{%i}.accessURL'%(j)))
    PYTHONSYMBOL = FeatureProcessor
    -> BulkAttributeRemover

Bookmark: Attributes manager
Note: e-mail management
StringReplacer
    CASE = NO
    FIND_TEXT = mailto:
    NO_MATCH = _FME_NO_OP_
    REGEXP = NO
    SRC_ATTRS = contact_email
    -> ATTRIBUTE_VALUE_TEXT_CLEANER
ATTRIBUTE_VALUE_TEXT_CLEANER
    -> AttributeExposer_6

Bookmark: Manage notes
AttributeExposer_6
    ATTR_TABLE = notes1,,notes2,
    -> TestFilter_3
TestFilter_3
    PASSED_TEST_GROUP_OUTPUT = FIRST
    TEST_LIST:
      "BOOL_OP,AND,COMPOSITE_TEST,""""""1 AND 2"""""",TEST_CLAUSE,TEST @Value(notes1) = @Value(notes2)
      TEST notes1 ATTRIBUTE_HAS_A_VALUE """,notes = notes1,"BOOL_OP,OR,COMPOSITE_TEST,""""""1"""""",TEST_CLAUSE,TEST @Value(notes1) NOT_= @Value(notes2)",notes = notes1+notes2,"BOOL_OP,AND,COMPOSITE_TEST,""""""1 AND 2"""""",TEST_CLAUSE,TEST notes1 NOT_ATTRIBUTE_HAS_A_VALUE ""
      TEST notes2 NOT_ATTRIBUTE_HAS_A_VALUE """,notes = title
    notes = notes1 -> StringConcatenator
    notes = notes1+notes2 -> StringConcatenator_3
    notes = title -> StringConcatenator_2
    <UNFILTERED> -> StringConcatenator_2
StringConcatenator
    ACTION = Create New Attribute
    PARM_LINE = "@Value(notes1)\n\n"
    VAL_ATTR = notes
    -> Junction_5
StringConcatenator_3
    ACTION = Create New Attribute
    PARM_LINE = "@Value(notes1)\n\n@Value(notes2)\n\n"
    VAL_ATTR = notes
    -> Junction_5
StringConcatenator_2
    ACTION = Create New Attribute
    PARM_LINE = "@Value(title)\n\n"
    VAL_ATTR = notes
    -> Junction_5
Note: Notes in SK/MB original metadata usually corresponds to: notes1(DCAT_S_attributes.snippet) <br> notes2(DCAT_S_attributes.searchDescription) / If these attributes are missing then notes = title
Junction_5
    -> ATTRIBUTE_UNEXPOSER
ATTRIBUTE_UNEXPOSER
    -> AttributeExposer

Bookmark: License filtering
AttributeExposer
    ATTR_TABLE = license,
    -> NullAttributeMapper
NullAttributeMapper
    ATTRCHOICE_ACTION = SELECTED
    ATTRLIST = license
    NEW_VALUE = unknown
    NULL_TREATMENT_LU = SETVALUE
    SOURCE_ATTR_VAL_LU = SETNULL EMPTY MISSINGATTR
    ATTRCHOICE = Selected Attributes
    NULL_TREATMENT = New Value
    SOURCE_ATTR_VAL = Null Empty "Missing (Selected Attributes Only)"
    -> LICENSE_FILTER_NG
LICENSE_FILTER_NG
    FEATURE_TYPE = License_$(P-T_ABBR)
    IN_CSV_LOOKUP_TABLES_DIR = $(IN_CSV_LOOKUPTABLES_DIR)
    LICENSE_ATT = @Value(license)
    P-T_ABBR = $(P-T_ABBR)
    LICENSE_FILTER_PASSED -> AttributeExposer_14
    UNKNOWN_LICENSE -> UNKNOWN_LICENCE (writer XLSXW_1)
UNKNOWN_LICENCE (writer XLSXW_1)
    attributes: license_id string(200), id string(200)

Bookmark: Date conversion
AttributeExposer_14
    ATTR_TABLE = id,,record_create_date,,record_last_modified,,record_publish_date,,data_collection_start_date,,data_collection_end_date,,record_last_modified2,
    -> DateTimeConverter
DateTimeConverter
    DATETIME_ATTR = record_create_date record_last_modified record_publish_date data_collection_end_date data_collection_start_date record_last_modified2
    OUT_FORMAT = %Y-%m-%d
    PASSTHROUGH = YES
    REPAIR_INPUT = YES
    -> Junction_2
    <REJECTED> -> AttributeRemover_2
AttributeRemover_2
    REMOVE_ATTRS = fme_rejection_code
    -> Junction_2
Junction_2
    -> AttributeExposer_4

Bookmark: Generate new unique id from metadata DCAT_S_id
AttributeExposer_4
    ATTR_TABLE = id,
    -> DuplicateFilter
DuplicateFilter
    INPUT_ORDERED_CHOICE_LOOKUP = NO
    KEYATTR = id
    INPUT_ORDERED_CHOICE = No
    UNIQUE -> UNIQUE_ID_CREATOR
    DUPLICATE -> Terminator
Note: Generate new uuid (overwrite attribute id) from DCAT_P_id_layer since some metadata have the same id with _# suffixes
UNIQUE_ID_CREATOR
    UNIQUE_ATT = @Value(id)
    -> AttributeExposer_2
Note: If there is a duplicate id, terminate program and change the solution
Terminator
    MESSAGE = Translation Terminated

Bookmark: Rename ArcGIS Hub Dataset by Original Metadata
AttributeExposer_2
    ATTR_TABLE = resources{}.name,,id,
    -> ListSearcher
ListSearcher
    ATTR_VALUE = ArcGIS Hub Dataset
    CASE = CASE_SENSITIVE
    INDEX_ATTR = _index_Landing_page
    LIST_ATTR = resources{}.name
    MATCHTYPE = FIRST_MATCHED_ENCODED
    FOUND -> AttributeCreator
    NOT_FOUND -> Junction_3
AttributeCreator
    ATTR_TABLE = SET_TO resources{@Value(_index_Landing_page)}.name (varchar(200)) = FME_CONDITIONAL:DEFAULT_VALUE'_FME_NO_OP_'BOOL_OP;OR;COMPOSITE_TEST;1;TEST $(P-T_ABBR) = SK'original metadata (http://geohub.saskatchewan.ca)'BOOL_OP;OR;COMPOSITE_TEST;1;TEST $(P-T_ABBR) = MB'original metadata (https://geoportal.gov.mb.ca)'FME_NUM_CONDITIONS3___
    -> Junction_3
Junction_3
    -> ATTRIBUTE_UNEXPOSER_2
ATTRIBUTE_UNEXPOSER_2
    -> DEFAULT_ATTRIBUTE_MAPPER_NG

Bookmark: attribute mapper and manager
DEFAULT_ATTRIBUTE_MAPPER_NG
    FEATURE_TYPE = Default_$(P-T_ABBR)
    IN_CSV_LOOKUP_TABLES_DIR = $(IN_CSV_LOOKUPTABLES_DIR)
    P-T_ABBR = $(P-T_ABBR)
    -> Spatial_extent_validator
Note: Different yaml text if MB or SK for record date attributes
ATTRIBUTE_MANAGER_NG
    IN_YAML_TEXT:
      FME_CONDITIONAL:DEFAULT_VALUE''BOOL_OP;OR;COMPOSITE_TEST;1;TEST $(P-T_ABBR) = MB'online_resource_protocol:
          action: attribute_overwrite
          attr2set: resources{0}.type

      iso_topic{0}.topic_value:
          action: attribute_not_null
          attr2set: default_topic

      west_bound_longitude:
         action: attribute_not_null
         attr2set: default_west_bound_longitude

      east_bound_longitude:
         action: attribute_not_null
         attr2set: default_east_bound_longitude

      south_bound_latitude:
         action: attribute_not_null
         attr2set: default_south_bound_latitude

      north_bound_latitude:
         action: attribute_not_null
         attr2set: default_north_bound_latitude

      contact_email:
         action: attribute_not_null
         attr2set: defaut_contact_email

      sector:
         action: attribute_not_null
         attr2set: defaut_contact_name

      data_collection_start_date:
          action: attribute_not_null
          attr2set: default_data_collection_start_date

      data_collection_end_date:
          action: attribute_not_null
          attr2set: default_data_collection_end_date

      record_last_modified:
          action: attribute_not_null
          attr2set: record_last_modified2

      record_publish_date:
          action: attribute_not_null
          attr2set: record_create_date

      'BOOL_OP;OR;COMPOSITE_TEST;1;TEST $(P-T_ABBR) = SK'online_resource_protocol:
          action: attribute_overwrite
          attr2set: resources{0}.type

      iso_topic{0}.topic_value:
          action: attribute_not_null
          attr2set: default_topic

      west_bound_longitude:
         action: attribute_not_null
         attr2set: default_west_bound_longitude

      east_bound_longitude:
         action: attribute_not_null
         attr2set: default_east_bound_longitude

      south_bound_latitude:
         action: attribute_not_null
         attr2set: default_south_bound_latitude

      north_bound_latitude:
         action: attribute_not_null
         attr2set: default_north_bound_latitude

      contact_email:
         action: attribute_not_null
         attr2set: defaut_contact_email

      sector:
         action: attribute_not_null
         attr2set: defaut_contact_name

      data_collection_start_date:
          action: attribute_not_null
          attr2set: default_data_collection_start_date

      data_collection_end_date:
          action: attribute_not_null
          attr2set: default_data_collection_end_date

      record_last_modified:
          action: attribute_overwrite
          attr2set: record_last_modified2

      record_publish_date:
          action: attribute_not_null
          attr2set: record_create_date

      'FME_NUM_CONDITIONS3___
    -> PythonCaller
Note: if resources{}.name == Shapefile / then resources{}.format <- Shapefile
PythonCaller
    PYTHONSOURCE:
      import fme
      import fmeobjects
      # Template Function interface:
      # When using this function, make sure its name is set as the value of
      # the 'Class or Function to Process Features' transformer parameter
      def processFeature(feature):

          resources_name = feature.getAttribute('resources{}.name')

          #If no attribute then create empty attribute
          if not resources_name:
              pass
          else:
              for elem in range(len(resources_name)):
                  if resources_name[elem]=='Shapefile':
                      feature.setAttribute('resources{%i}.format'%(elem), 'Shapefile')
    PYTHONSYMBOL = processFeature
    -> PythonCaller_4
SPATIAL_EXTENT_TO_VALIDATE (writer XLSXW_1)
    attributes: id string(45), north_bound_latitude string(35), south_bound_latitude string(35), east_bound_longitude string(35), west_bound_longitude string(35)

Bookmark: Validate spatial extent
Spatial_extent_validator
    FEATURE_TYPE = SpatialExtent_$(P-T_ABBR)
    IN_CSV_LOOKUPTABLES_DIR = $(IN_OUT_WORKING_DIR)\LOOKUP_TABLES
    P-T_ABBR = $(P-T_ABBR)
    default_east_long = default_east_bound_longitude
    default_north_lat = default_north_bound_latitude
    default_south_lat = default_south_bound_latitude
    default_west_long = default_west_bound_longitude
    east_longitude = east_bound_longitude
    north_latitude = north_bound_latitude
    south_latitude = south_bound_latitude
    west_longitude = west_bound_longitude
    -> ATTRIBUTE_MANAGER_NG
    EXTENT_TO_VALIDATE -> AttributeExposer_3
AttributeExposer_3
    ATTR_TABLE = id,,north_bound_latitude,,south_bound_latitude,,east_bound_longitude,,west_bound_longitude,
    -> SPATIAL_EXTENT_TO_VALIDATE (writer XLSXW_1)

Bookmark: Format and resources manager and validator
Note: If format isr EsriRest; remove format value so that it is added in empty format mapper ng; to ensure that only valid EsriRest format are added
PythonCaller_4
    PYTHONSOURCE:
      import fme
      import fmeobjects
      from Python.FME_utils import FME_utils

      #def processFeature(feature):
      #    pass

      # Template Class Interface:
      # When using this class, make sure its name is set as the value of
      # the 'Class or Function to Process Features' transformer parameter
      def FeatureProcessor(feature):

          max_index=FME_utils.max_index_attribute_list(feature,'resources{}.format')
          for j in range(max_index+1):
              x = feature.getAttribute('resources{%i}.format'%(j))
              if x:
               if 'REST' in x.upper():
                feature.setAttributeNullWithType('resources{%i}.format'%(j),fmeobjects.FME_ATTR_ENCODED_STRING)
    PYTHONSYMBOL = FeatureProcessor
    -> EMPTY_FORMAT_MAPPER_NG [DATA_INPUT]
EMPTY_FORMAT_MAPPER_NG
    CSV_FORMAT = Format
    CSV_MIME_TYPE = Mime_type
    IN_CSV_LOOKUP_TABLES_DIR = $(IN_CSV_LOOKUPTABLES_DIR)
    P-T_ABBR = $(P-T_ABBR)
    URL_VALIDATION = $(URL_VALIDATION)
    DATA_OUTPUT -> FORMAT_VALIDATOR
    UNKNOWN_MIME_TYPE -> UNKNOWN_MIME_TYPE (writer XLSXW_1)
UNKNOWN_MIME_TYPE (writer XLSXW_1)
    attributes: id string(200), _unknown_mime_type string(200), _url_validation string(200)
FORMAT_VALIDATOR
    -> RESOURCES_VALIDATOR
RESOURCES_VALIDATOR
    -> GEO_NONE_GEO_SELECTOR

Bookmark: Geo non-geo selector
Note: For MB/SK: geojson and esri rest are not automatically considered as geo since they can be added as resources for non-geo data (without coordinates; only table). / These provinces have their own GeoSpatialValidation lookup table (GeoSpatialValidation_MB and GeoSpatialValidation_SK)
GEO_NONE_GEO_SELECTOR
    CSV_FILE_NAME = GeoSpatialValidation_$(P-T_ABBR)
    CSV_PATH = $(IN_CSV_LOOKUPTABLES_DIR)
    CSV_PROVINCE = $(P-T_ABBR)
    YAML_DIRECTIVES:
      resources{}.format:
        domain: lookup_table_format
        spatial_type: overwrite
        not_found: log
        search_type: equals
    GEOSPATIAL -> SPATIAL_TYPE_MAPPER_NG [DATA_INPUT]
    NONE_GEOSPATIAL -> MANUAL_GEOSPATIAL_SETTER_NG [DATA_INPUT]
    LOG_ERROR -> GEOSPATIAL_FORMAT_NOT_MAPPED (writer XLSXW_1)
SPATIAL_TYPE_MAPPER_NG
    FEATURE_TYPE = SpatialType_$(P-T_ABBR)
    IN_CSV_LOOKUP_TABLES_DIR = $(IN_CSV_LOOKUPTABLES_DIR)
    P-T_ABBR = $(P-T_ABBR)
    DATA_OUTPUT_FAILED -> AttributeExposer_18
    DATA_OUTPUT_PASSED -> TestFilter
SPATIAL_TYPE_NOT_MAPPED (writer XLSXW_1)
    attributes: id string(20), title string(80), notes string(80)
MANUAL_GEOSPATIAL_SETTER_NG
    FEATURE_TYPE = UnmappedGeoData_$(P-T_ABBR)
    IN_CSV_LOOKUP_TABLES_DIR = $(IN_CSV_LOOKUPTABLES_DIR)
    P-T_ABBR = $(P-T_ABBR)
    GEOSPATIAL -> TestFilter
    NON-GEOSPATIAL -> TestFilter_4
    UNMAPPED_DATA -> UNMAPPED_DATA (writer XLSXW_1)
TestFilter
    DEFAULT_VALUE = <UNFILTERED>
    PASSED_TEST_GROUP_OUTPUT = FIRST
    TEST_LIST = "BOOL_OP,OR,COMPOSITE_TEST,""""""1"""""",TEST_CLAUSE,CASE_INSENSITIVE_TEST @LowerCase($(ACTIVATE_GEO)) = yes",GEO_ACTIVATE
    GEO_ACTIVATE -> TestFilter_5
UNMAPPED_DATA (writer XLSXW_1)
    attributes: id string(200), notes string(200), title string(200)
TestFilter_4
    DEFAULT_VALUE = <UNFILTERED>
    PASSED_TEST_GROUP_OUTPUT = FIRST
    TEST_LIST = "BOOL_OP,OR,COMPOSITE_TEST,""""""1"""""",TEST_CLAUSE,CASE_INSENSITIVE_TEST $(ACTIVATE_NON_GEO) = yes",ACTIVATE_NON_GEO
    ACTIVATE_NON_GEO -> TestFilter_2
GEOSPATIAL_FORMAT_NOT_MAPPED (writer XLSXW_1)
    attributes: format auto(20), id auto(20)

Bookmark: Samples or full content
TestFilter_5
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_8
    SAMPLES FEATURES -> Sampler_2
Sampler_2
    MODE = ORIGINAL
    RATE = $(SAMPLE_SIZE)
    SAMPLE_TYPE_MULTIPLIER = -1
    SAMPLE_MODE = No
    SAMPLE_TYPE_LONG = First N Features
    SAMPLED -> Junction_8

Bookmark: Geo metadata processing
Junction_8
    -> METADATA_VALUE_MAPPER_NG_2 [DATA_INPUT]
TRANSLATION_ERRORS (writer XLSXW_1)
    attributes: id string(20), title string(20)

Bookmark: Metadata Value Mapping - GEO
Note: Topic (categfory)
METADATA_VALUE_MAPPER_NG_2
    ATT_TO_MAP = iso_topic{}.topic_value
    CODE_REFRESH = NO
    ENGLISH_REFRESH = YES
    ERROR_NOT_MAPPED = YES
    FEATURE_TYPE = Topic
    FRENCH_REFRESH = NO
    IN_CSV_LOOKUP_TABLES_DIR = $(IN_CSV_LOOKUPTABLES_DIR)
    P-T_ABBR = $(P-T_ABBR)
    -> METADATA_VALUE_MAPPER_NG_3 [DATA_INPUT]
Note: Role
METADATA_VALUE_MAPPER_NG_3
    ATT_TO_MAP = role
    CODE_REFRESH = YES
    ENGLISH_REFRESH = YES
    ERROR_NOT_MAPPED = YES
    FEATURE_TYPE = Role
    FRENCH_REFRESH = YES
    IN_CSV_LOOKUP_TABLES_DIR = $(IN_CSV_LOOKUPTABLES_DIR)
    P-T_ABBR = $(P-T_ABBR)
    -> METADATA_VALUE_MAPPER_NG_4 [DATA_INPUT]
Note: Update
METADATA_VALUE_MAPPER_NG_4
    ATT_TO_MAP = update_frequency
    CODE_REFRESH = YES
    ENGLISH_REFRESH = YES
    ERROR_NOT_MAPPED = YES
    FEATURE_TYPE = Update
    FRENCH_REFRESH = YES
    IN_CSV_LOOKUP_TABLES_DIR = $(IN_CSV_LOOKUPTABLES_DIR)
    P-T_ABBR = $(P-T_ABBR)
    -> METADATA_VALUE_MAPPER_NG_5 [DATA_INPUT]
Note: Progress
METADATA_VALUE_MAPPER_NG_5
    ATT_TO_MAP = progress_code
    CODE_REFRESH = YES
    ENGLISH_REFRESH = YES
    ERROR_NOT_MAPPED = YES
    FEATURE_TYPE = Progress
    FRENCH_REFRESH = YES
    IN_CSV_LOOKUP_TABLES_DIR = $(IN_CSV_LOOKUPTABLES_DIR)
    P-T_ABBR = $(P-T_ABBR)
    -> METADATA_VALUE_MAPPER_NG_7 [DATA_INPUT]
Note: SpatialRepresentation
METADATA_VALUE_MAPPER_NG_7
    ATT_TO_MAP = spatial_representation_type
    CODE_REFRESH = YES
    ENGLISH_REFRESH = YES
    ERROR_NOT_MAPPED = YES
    FEATURE_TYPE = SpatialRepresentation
    FRENCH_REFRESH = YES
    IN_CSV_LOOKUP_TABLES_DIR = $(IN_CSV_LOOKUPTABLES_DIR)
    P-T_ABBR = $(P-T_ABBR)
    -> METADATA_FORMAT_MAPPER_NG [DATA_INPUT]
Note: Format
METADATA_FORMAT_MAPPER_NG
    ATT_TO_MAP = resources{}.format
    ERROR_NOT_MAPPED = YES
    FEATURE_TYPE = Format
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_Geo (writer XLSXW_1)
    -> METADATA_VALUE_MAPPER_ERROR_MANAGER
UNKNOWN_MIME_TYPE_Geo (writer XLSXW_1)
    attributes: _unknown_mime_type string(8), _url_validation string(8), id string(8)
METADATA_VALUE_MAPPER_ERROR_MANAGER
    ERROR_OUTPUT -> GEO_ATTRIBUTE_MAPPING_ERRORS (writer XLSXW_1)
    DATA_OUTPUT -> AttributeExposer_5
GEO_ATTRIBUTE_MAPPING_ERRORS (writer XLSXW_1)
    attributes: error string(200), id string(200)

Bookmark: Sector management
AttributeExposer_5
    ATTR_TABLE = sector,
    -> StringReplacer_3
Note: Remove 'Government of Saskatchewan' or 'Government of Manitoba' from sector
StringReplacer_3
    CASE = NO
    FIND_TEXT = FME_CONDITIONAL:DEFAULT_VALUE''BOOL_OP;OR;COMPOSITE_TEST;1;TEST $(P-T_ABBR) = MB'Government of Manitoba'BOOL_OP;OR;COMPOSITE_TEST;1;TEST $(P-T_ABBR) = SK'Government of Saskatchewan'FME_NUM_CONDITIONS3___
    NO_MATCH = _FME_NO_OP_
    REGEXP = NO
    SRC_ATTRS = sector
    -> AttributeTrimmer
Note: Enlevons les espaces que le stringreplace laisse à la fin, car cela cause des problèmes dans le metadata_delta_finder
AttributeTrimmer
    SRC_ATTRS = sector
    TRIM_CHARS = " "
    TRIM_TO_NONE = Yes
    TRIM_TYPE = BOTH
    -> RESOURCE_NAME_UNDERSCORE_REMOVER

Bookmark: Remove all underscores from resources{}.name attributes
RESOURCE_NAME_UNDERSCORE_REMOVER
    DATA_OUTPUT -> AttributeExposer_15

Bookmark: HNAP RULES
AttributeExposer_15
    ATTR_TABLE = resources{}.url,,id,,spatial_representation_type,
    -> Tester_4
Note: If spatial_representation_type = textTable, do not add an ESRI REST protocol
Tester_4
    BOOL_OP = OR
    TEST_CLAUSE = CASE_INSENSITIVE_TEST @Value(spatial_representation_type) CONTAINS textTable
    TEST_MODE = CASE_INSENSITIVE_TEST
    PASSED -> PythonCaller_2
    FAILED -> WMS_REST_LANGUAGE_FORMATTER
Note: add 'HTTPS' value to resources{}.protocol
PythonCaller_2
    PYTHONSOURCE:
      import fme
      import fmeobjects
      from Python.FME_utils import FME_utils

      # Template Function interface:
      # When using this function, make sure its name is set as the value of
      # the 'Class or Function to Process Features' transformer parameter
      def FeatureProcessor(feature):

          max_index=FME_utils.max_index_attribute_list(feature,'resources{}')
          for j in range(max_index+1):
              feature.setAttribute('resources{%i}.protocol'%(j),'HTTPS')
    PYTHONSYMBOL = FeatureProcessor
    -> DUPLICATE_SERVICE_REMOVER
DUPLICATE_SERVICE_REMOVER
    -> GMD_SECTION_DATA_EXTRACTION
GMD_SECTION_DATA_EXTRACTION
    -> REMOVE_BROKEN_URL_WMS_ESRI_REST

Bookmark: New Bookmark
WMS_REST_LANGUAGE_FORMATTER
    -> PythonCaller_7
Note: If resources{}.url contains MapServer or ends with FeatureServer (without /) then do not add an ESRI REST protocol (cannot be visualized in the viewer)
PythonCaller_7
    PYTHONSOURCE:
      import fme
      import fmeobjects
      from Python.FME_utils import FME_utils


      def FeatureProcessor(feature):
          dict_1 = {}
          dict_2 = {}

          max_index=FME_utils.max_index_attribute_list(feature,'resources{}')

          for j in range(max_index+1):
              format = feature.getAttribute('resources{%i}.format'%(j))
              url = feature.getAttribute('resources{%i}.url'%(j))


              if (format == 'ESRI REST') and ('MapServer' in url):
                dict_1[url] = j
                feature.setAttribute('resources{%i}.protocol'%(j),'HTTPS')
                feature.setAttributeNullWithType('resources{%i}.xlink_role'%(j),fmeobjects.FME_ATTR_ENCODED_STRING)

      #Ajustement fait au code python puisque des modifications sont faites concernant les services FeatureServers dans WMS_REST_LANGUAGE_FORMATTER.fmx
      #        elif (format == 'ESRI REST') and (url.endswith('FeatureServer')):
      #          dict_2[url] = j
      #          feature.setAttribute('resources{%i}.protocol'%(j),'HTTPS')
      #          feature.setAttributeNullWithType('resources{%i}.xlink_role'%(j),fmeobjects.FME_ATTR_ENCODED_STRING)


          max_index=FME_utils.max_index_attribute_list(feature,'resources{}')
          for j in range(max_index+1):
              format = feature.getAttribute('resources{%i}.format'%(j))
              url = feature.getAttribute('resources{%i}.url'%(j))

              if 'MapServer' in url:
                 if j == dict_1[url]:
                    feature.removeAttrsWithPrefix('resources{%i}'%(j))

      #Ajustement fait au code python puisque des modifications sont faites concernant les services FeatureServers dans WMS_REST_LANGUAGE_FORMATTER.fmx
      #        elif url.endswith('FeatureServer'):
      #           if j == dict_2[url]:
      #              feature.removeAttrsWithPrefix('resources{%i}'%(j))
    PYTHONSYMBOL = FeatureProcessor
    -> RESOURCES_VALIDATOR_3
RESOURCES_VALIDATOR_3
    -> DUPLICATE_SERVICE_REMOVER

Bookmark: Drop Broken Web Services
REMOVE_BROKEN_URL_WMS_ESRI_REST
    URL_VALIDATION = Yes
    -> AttributeCreator_3
    FAULTY_URL_OUTPUT -> MAP_SERVICE_URL_ERRORMAP (writer XLSXW_1)
MAP_SERVICE_URL_ERRORMAP (writer XLSXW_1)
    attributes: id string(200), url string(200), format string(200), _url_failure_message string(20)

Bookmark: Metadata_delta_finder
AttributeCreator_3
    ATTR_TABLE = SET_TO csw_url (varchar(200)) = $(FORCED_PYCSW_URL)
    -> ATTRIBUTE_MANAGER_NG_4
AttributeExposer_16
    ATTR_TABLE = search_criteria_pycsw,,csw_url,,record_last_modified,,id,,resources{}.xlink_role,
    -> StringReplacer_2
Note: Remplacement de la valeur <nulll> par rien
StringReplacer_2
    CASE = NO
    FIND_TEXT = <null>
    NO_MATCH = _FME_NO_OP_
    REGEXP = NO
    SRC_ATTRS = resources{0}.xlink_role,resources{1}.xlink_role,resources{2}.xlink_role,resources{3}.xlink_role,resources{4}.xlink_role,resources{5}.xlink_role,resources{6}.xlink_role,resources{7}.xlink_role,resources{8}.xlink_role,resources{9}.xlink_role,resources{10}.xlink_role,resources{11}.xlink_role,resources{12}.xlink_role,resources{13}.xlink_role,resources{14}.xlink_role,resources{15}.xlink_role,resources{16}.xlink_role,resources{17}.xlink_role,resources{18}.xlink_role,resources{19}.xlink_role,resources{20}.xlink_role,resources{21}.xlink_role,resources{22}.xlink_role,resources{23}.xlink_role,resources{24}.xlink_role,resources{25}.xlink_role,resources{26}.xlink_role,resources{27}.xlink_role,resources{28}.xlink_role,resources{29}.xlink_role,resources{30}.xlink_role,resources{31}.xlink_role,resources{32}.xlink_role,resources{33}.xlink_role,resources{34}.xlink_role,resources{35}.xlink_role,resources{36}.xlink_role,resources{37}.xlink_role,resources{38}.xlink_role,resources{39}.xlink_role,resources{40}.xlink_role,resources{41}.xlink_role,resources{42}.xlink_role,resources{43}.xlink_role,resources{44}.xlink_role,resources{45}.xlink_role,resources{46}.xlink_role,resources{47}.xlink_role,resources{48}.xlink_role,resources{49}.xlink_role,resources{50}.xlink_role,resources{51}.xlink_role,resources{52}.xlink_role,resources{53}.xlink_role,resources{54}.xlink_role,resources{55}.xlink_role,resources{56}.xlink_role,resources{57}.xlink_role,resources{58}.xlink_role,resources{59}.xlink_role,resources{60}.xlink_role,resources{61}.xlink_role,resources{62}.xlink_role,resources{63}.xlink_role,resources{64}.xlink_role,resources{65}.xlink_role,resources{66}.xlink_role,resources{67}.xlink_role,resources{68}.xlink_role,resources{69}.xlink_role,resources{70}.xlink_role,resources{71}.xlink_role,resources{72}.xlink_role,resources{73}.xlink_role,resources{74}.xlink_role,resources{75}.xlink_role,resources{76}.xlink_role,resources{77}.xlink_role,resources{78}.xlink_role,resources{79}.xlink_role,resources{80}.xlink_role,resources{81}.xlink_role,resources{82}.xlink_role,resources{83}.xlink_role,resources{84}.xlink_role,resources{85}.xlink_role,resources{86}.xlink_role,resources{87}.xlink_role,resources{88}.xlink_role,resources{89}.xlink_role,resources{90}.xlink_role,resources{91}.xlink_role,resources{92}.xlink_role,resources{93}.xlink_role,resources{94}.xlink_role,resources{95}.xlink_role,resources{96}.xlink_role,resources{97}.xlink_role,resources{98}.xlink_role,resources{99}.xlink_role,resources{100}.xlink_role
    -> METADATA_DELTA_FINDER_GEN
METADATA_DELTA_FINDER_GEN
    ATTR_DATE_MODIFIED = record_last_modified
    CSW_FILTER = @Value(search_criteria_pycsw)
    LOCAL_SOURCE = $(LOCAL_SOURCE_METADATA_DELTA_FINDER)
    METADATA_OVERWRITE = $(METADATA_OVERWRITE)
    METADATA_TYPE = XML-HNAP
    SOURCE_DIRECTORY = $(OUT_XML_LOCAL_DIR)
    SOURCE_URL = @Value(csw_url)
    VALIDATE_INSERT_PCT = $(VALIDATE_INSERT_PCT_XML)
    YAML_FILE = $(IN_CSV_LOOKUP_TABLES_DIR)\$(P-T_ABBR)\metadata_delta_finder_$(P-T_ABBR)_geo.yaml
    Statistics -> StatisticsCalculator_Summary_2
    Update -> Junction
    Insert -> Junction
    Delete -> AttributeExposer_19
StatisticsCalculator_Summary_2: Logger
    LOG_FEATURE = NONE
    MAXFEATS = 20
    MESSAGE:
      ************************
      **** Unchanged Report ****
      ************************

      @Value(_real_count) features were unchanged

      ************************
      ************************
      ************************
    SEVERITY = INFO
AttributeExposer_19
    ATTR_TABLE = id,,title,
    -> DELETEDRECORDS (writer XLSXW_1)
DELETEDRECORDS (writer XLSXW_1)
    attributes: id string(200), title string(200)
Junction
    -> AWS_TRANSLATE_2

Bookmark: Listes Metadata_delta_finder
ATTRIBUTE_MANAGER_NG_4
    IN_YAML_TEXT:
      contacts{0}.role_code:
         action: attribute_not_null
         attr2set: role_code
      contacts{0}.role:
         action: attribute_not_null
         attr2set: role
      contacts{0}.role_fr:
         action: attribute_not_null
         attr2set: role_fr
      contacts{0}.p-t_entity:
         action: attribute_not_null
         attr2set: p-t_entity
      contacts{0}.p-t_entity_fr:
         action: attribute_not_null
         attr2set: p-t_entity_fr
      contacts{0}.sector:
         action: attribute_not_null
         attr2set: sector
      contacts{0}.email:
         action: attribute_not_null
         attr2set: contact_email
      distributionList{0}.format_version:
         action: attribute_not_null
         attr2set: distribution_format_version
      resources{0}.language:
         action: attribute_not_null
         attr2set: transfer_desc_locale_default
      resources{0}.xlink_role:
         action: text_not_null
         attr2set: <null>
    -> ATTRIBUTE_MANAGER_NG_5
ATTRIBUTE_MANAGER_NG_5
    IN_YAML_TEXT:
      contacts{}.role_code:
         action: attribute_not_null
         attr2set: role_code
      contacts{}.role:
         action: attribute_not_null
         attr2set: role
      contacts{}.role_fr:
         action: attribute_not_null
         attr2set: role_fr
      contacts{}.p-t_entity:
         action: attribute_not_null
         attr2set: p-t_entity
      contacts{}.p-t_entity_fr:
         action: attribute_not_null
         attr2set: p-t_entity_fr
      contacts{}.sector:
         action: attribute_not_null
         attr2set: sector
      contacts{}.email:
         action: attribute_not_null
         attr2set: contact_email
      distributionList{}.format_version:
         action: attribute_not_null
         attr2set: distribution_format_version
      resources{}.language:
         action: attribute_not_null
         attr2set: transfer_desc_locale_default
      resources{}.xlink_role:
         action: text_not_null
         attr2set: <null>
    -> AttributeExposer_16

Bookmark: AWS Translation
AWS_TRANSLATE_2
    ACTIVATE_TRANSLATION = $(ACTIVATE_TRANSLATION)
    ATTR_2_TRANSLATE = notes,title
    ATTR_LIST_2_TRANSLATE = tags{}.value,resources{}.name
    MODE = English-->French
    -> XML_PUBLISHER_NG
    TRANSLATION_PROBLEM -> AttributeExposer_20
AttributeExposer_20
    ATTR_TABLE = id,,title,
    -> TRANSLATION_ERRORS (writer XLSXW_1)

Bookmark: XML CREATION AND WRITING
XML_PUBLISHER_NG
    FEATURE_TYPE = Config_$(P-T_ABBR)
    IN_CSV_LOOKUP_TABLES_DIR = $(IN_CSV_LOOKUPTABLES_DIR)
    LOCAL_WRITER = $(LOCAL_WRITER)
    P-T_ABBR = $(P-T_ABBR)
    TEMPLATE_GMD_CITEDRESPONSIBLEPARTY = $(IN_GMD_XML_TEMPLATE_DIR)/GMD_CITEDRESPONSIBLEPARTY.xml
    TEMPLATE_GMD_CONTACT = $(IN_GMD_XML_TEMPLATE_DIR)/GMD_CONTACT.xml
    TEMPLATE_GMD_DISTRIBUTIONFORMAT = $(IN_GMD_XML_TEMPLATE_DIR)/GMD_DISTRIBUTIONFORMAT.xml
    TEMPLATE_GMD_DISTRIBUTOR = $(IN_GMD_XML_TEMPLATE_DIR)/GMD_DISTRIBUTOR.xml
    TEMPLATE_GMD_KEYWORDS = $(IN_GMD_XML_TEMPLATE_DIR)/GMD_KEYWORDS.xml
    TEMPLATE_GMD_MDMETADATA = $(IN_GMD_XML_TEMPLATE_DIR)/GMD_MDMETADATA.xml
    TEMPLATE_GMD_REFERENCESYSTEMINFO = $(IN_GMD_XML_TEMPLATE_DIR)/GMD_REFERENCESYSTEMINFO.xml
    TEMPLATE_GMD_RESOURCEMAINTENANCE = $(IN_GMD_XML_TEMPLATE_DIR)/GMD_RESOURCEMAINTENANCE.xml
    TEMPLATE_GMD_TOPICCATEGORY = $(IN_GMD_XML_TEMPLATE_DIR)/GMD_TOPICCATEGORY.xml
    TEMPLATE_GMD_TRANSFEROPTIONS = $(IN_GMD_XML_TEMPLATE_DIR)/GMD_TRANSFEROPTIONS.xml
    LOCAL -> text_line (writer TEXTLINE_3)
    INSERT_PASSED -> text_line (writer TEXTLINE_1)
    UPDATE_PASSED -> text_line (writer TEXTLINE_1)
    INSERT_FAILED -> text_line (writer TEXTLINE_2)
    InvalidMetadata -> invalid_metadata (writer XLSXW_1)
    UPDATE_FAILED -> text_line (writer TEXTLINE_2)
Note: Writes XML to a local folder without publishing to PyCSW, and without the PyCSW transaction headers and footers
text_line (writer TEXTLINE_3)
    attributes: text_line_data buffer
text_line (writer TEXTLINE_1)
    attributes: text_line_data buffer
text_line (writer TEXTLINE_2)
    attributes: text_line_data buffer
invalid_metadata (writer XLSXW_1)
    attributes: id auto(20)

Bookmark: Samples or full content
TestFilter_2
    DEFAULT_VALUE = SAMPLES FEATURES
    PASSED_TEST_GROUP_OUTPUT = FIRST
    TEST_LIST = "BOOL_OP,OR,COMPOSITE_TEST,""""""1"""""",TEST_CLAUSE,TEST $(SAMPLE_SIZE) = 0",ALL FEATURES
    ALL FEATURES -> Junction_6
    SAMPLES FEATURES -> Sampler_3
Sampler_3
    MODE = ORIGINAL
    RATE = $(SAMPLE_SIZE)
    SAMPLE_TYPE_MULTIPLIER = -1
    SAMPLE_MODE = No
    SAMPLE_TYPE_LONG = First N Features
    SAMPLED -> Junction_6

Bookmark: Non-geo metadata processing
Junction_6
    -> METADATA_VALUE_MAPPER_NG_10 [DATA_INPUT]
Note: Adjusting update frequency value
METADATA_VALUE_MAPPER_NG_10
    ATT_TO_MAP = update_frequency
    CODE_REFRESH = NO
    ENGLISH_REFRESH = YES
    ERROR_NOT_MAPPED = YES
    FEATURE_TYPE = UpdateFrequency_TBS
    FRENCH_REFRESH = NO
    IN_CSV_LOOKUP_TABLES_DIR = $(IN_CSV_LOOKUPTABLES_DIR)
    P-T_ABBR = $(P-T_ABBR)
    -> AttributeExposer_12
UNKNOWN_MIME_TYPE_NoneGeo (writer XLSXW_1)
    attributes: _unknown_mime_type string(8), _url_validation string(8), id string(8)
Note: Creates list of errors found and not corrected in mapping
METADATA_VALUE_MAPPER_ERROR_MANAGER_2
    ERROR_OUTPUT -> METADATA_MAPPING_ERRORS_NON_GEO (writer XLSXW_1)
    DATA_OUTPUT -> AttributeExposer_13
Note: Translates specific items from English to French
AWS_TRANSLATE_3
    ACTIVATE_TRANSLATION = $(ACTIVATE_TRANSLATION)
    ATTR_2_TRANSLATE = notes,title
    ATTR_LIST_2_TRANSLATE = tags{}.value,resources{}.name
    MODE = English-->French
    -> JSON_PUBLISHER_NG
    TRANSLATION_PROBLEM -> AttributeExposer_21
AttributeExposer_21
    ATTR_TABLE = id,,title,
    -> TRANSLATION_PROBLEMS_NONE_GEO (writer XLSXW_1)
TRANSLATION_PROBLEMS_NONE_GEO (writer XLSXW_1)
    attributes: id auto(20), title auto(20)
METADATA_MAPPING_ERRORS_NON_GEO (writer XLSXW_1)
    attributes: error string(200), id string(200)
AttributeExposer_24
    ATTR_TABLE = id,,title,,_rejected_reason,
    -> FORMAT_MAPPER_REJECTED (writer XLSXW_1)
FORMAT_MAPPER_REJECTED (writer XLSXW_1)
    attributes: _rejected_reason string(20), id string(200), title string(200)
AttributeExposer_23
    ATTR_TABLE = id,,title,
    -> FORMAT_MAPPER_NOT_FOUND (writer XLSXW_1)
FORMAT_MAPPER_NOT_FOUND (writer XLSXW_1)
    attributes: id string(200), title string(200)

Bookmark: Format mapper
AttributeExposer_12
    ATTR_TABLE = resources{}.format,
    -> ListElementFilter
Note: Remove Esri Rest or Geojson formats if non-geospatial data (these formats are not included in the origingal metadata)
ListElementFilter
    CASE = No
    EXP = geojson|esri rest
    FILTER_TYPE = REGEX_MATCH
    LIST_ATTR = resources{}.format
    NEGATE = Yes
    Filtered -> METADATA_FORMAT_MAPPER_NG_2 [DATA_INPUT]
    NotFound -> AttributeExposer_23
    <Rejected> -> AttributeExposer_24
Note: resources{}.format
METADATA_FORMAT_MAPPER_NG_2
    ATT_TO_MAP = resources{}.format
    ERROR_NOT_MAPPED = YES
    FEATURE_TYPE = Format_TBS
    IN_CSV_LOOKUP_TABLES_DIR = $(IN_CSV_LOOKUPTABLES_DIR)
    P-T_ABBR = $(P-T_ABBR)
    REAL_VALUE_REFRESH = YES
    RES_TYPE_EN_REFRESH = YES
    RES_TYPE_FR_REFRESH = YES
    URL_VALIDATION = $(URL_VALIDATION)
    Unknown_Mime_Type -> UNKNOWN_MIME_TYPE_NoneGeo (writer XLSXW_1)
    -> AttributeExposer_7

Bookmark: TOPICS value mapper from iso_topic{}.topic_value list attributes
AttributeExposer_7
    ATTR_TABLE = iso_topic{}.topic_value,
    -> ListCopier_2
ListCopier_2
    DEST_LIST = topics
    SRC_LIST = iso_topic{}
    -> METADATA_VALUE_MAPPER_NG_12 [DATA_INPUT]
METADATA_VALUE_MAPPER_NG_12
    ATT_TO_MAP = topics{}.topic_value
    CODE_REFRESH = NO
    ENGLISH_REFRESH = YES
    ERROR_NOT_MAPPED = YES
    FEATURE_TYPE = Topic_TBS
    FRENCH_REFRESH = NO
    IN_CSV_LOOKUP_TABLES_DIR = $(IN_CSV_LOOKUPTABLES_DIR)
    P-T_ABBR = $(P-T_ABBR)
    -> AttributeExposer_8
AttributeExposer_8
    ATTR_TABLE = topics{}.topic_value,
    -> ListDuplicateRemover
ListDuplicateRemover
    SRC_LIST = topics{}.topic_value
    -> AttributeExposer_10

Bookmark: SUBJECTS value mapper from iso_topic{}.topic_value list attributes
AttributeExposer_10
    ATTR_TABLE = iso_topic{}.topic_value,
    -> ListCopier_3
ListCopier_3
    DEST_LIST = subjects
    SRC_LIST = iso_topic{}
    -> METADATA_VALUE_MAPPER_NG_13 [DATA_INPUT]
METADATA_VALUE_MAPPER_NG_13
    ATT_TO_MAP = subjects{}.topic_value
    CODE_REFRESH = NO
    ENGLISH_REFRESH = YES
    ERROR_NOT_MAPPED = YES
    FEATURE_TYPE = Subject_TBS
    FRENCH_REFRESH = NO
    IN_CSV_LOOKUP_TABLES_DIR = $(IN_CSV_LOOKUPTABLES_DIR)
    P-T_ABBR = $(P-T_ABBR)
    -> AttributeExposer_9
AttributeExposer_9
    ATTR_TABLE = subjects{}.topic_value,
    -> ListDuplicateRemover_2
ListDuplicateRemover_2
    SRC_LIST = subjects{}.topic_value
    -> METADATA_VALUE_MAPPER_ERROR_MANAGER_2

Bookmark: metadata delta finder
AttributeExposer_13
    ATTR_TABLE = search_criteria_pycsw,,csw_url,,record_last_modified,,id,
    -> METADATA_DELTA_FINDER_GEN_2
METADATA_DELTA_FINDER_GEN_2
    ATTR_DATE_MODIFIED = record_last_modified
    LOCAL_SOURCE = Yes
    METADATA_OVERWRITE = $(METADATA_OVERWRITE)
    METADATA_TYPE = JSON-CKANExtCa
    SOURCE_DIRECTORY = $(OUT_JSON_LOCAL_DIR)
    VALIDATE_INSERT_PCT = $(VALIDATE_INSERT_PCT_JSON)
    YAML_FILE = $(IN_CSV_LOOKUP_TABLES_DIR)\$(P-T_ABBR)\metadata_delta_finder_$(P-T_ABBR)_non_geo.yaml
    Statistics -> StatisticsCalculator_Summary_3
    Update -> Junction_7
    Insert -> Junction_7
    Delete -> AttributeExposer_22
StatisticsCalculator_Summary_3: Logger
    LOG_FEATURE = NONE
    MAXFEATS = 20
    MESSAGE:
      ************************
      **** NoneGeo Features: Unchanged Report ****
      ************************

      @Value(_real_count) features were unchanged

      ************************
      ************************
      ************************
    SEVERITY = INFO
AttributeExposer_22
    ATTR_TABLE = id,,title,
    -> DELETED_RECORDS_NONE_GEO (writer XLSXW_1)
DELETED_RECORDS_NONE_GEO (writer XLSXW_1)
    attributes: id auto(20), title auto(20)
Junction_7
    -> AWS_TRANSLATE_3

Bookmark: JSON creation and writing
JSON_PUBLISHER_NG
    FEATURE_TYPE = JSON_CONFIG_$(P-T_ABBR)
    IN_CSV_LOOKUP_TABLES_DIR = $(IN_CSV_LOOKUPTABLES_DIR)
    JSON_RESOURCE_TEMPLATE = $(IN_TBS_JSON_TEMPLATE_DIR)\TBS_RESOURCES_TEMPLATE_NG.json
    JSON_ROOT_TEMPLATE = $(IN_TBS_JSON_TEMPLATE_DIR)\TBS_ROOT_TEMPLATE_NG.json
    Keywords_EN = tags{}.value
    Keywords_FR = tags{}.value_fr
    P-T_ABBR = $(P-T_ABBR)
    Subject_LIST = subjects{}.topic_value
    Topic_LIST = topics{}.topic_value
    OUTPUT_LOCAL -> AttributeExposer_11
AttributeExposer_11
    ATTR_TABLE = json_file,,id,
    -> AttributeCreator_6
AttributeCreator_6
    ATTR_TABLE = SET_TO text_line_data (varchar(200)) = @Value(json_file)
    -> text_line (writer TEXTLINE_4)
text_line (writer TEXTLINE_4)
    attributes: text_line_data buffer
